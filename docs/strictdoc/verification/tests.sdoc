[DOCUMENT]
TITLE: ROO Verification Plans (TST)
UID: DOC-ROO-TST
VERSION: 0.1
OPTIONS:
  MARKUP: Text

[[SECTION]]
TITLE: Honesty — published ≠ proven

[TEXT]
STATEMENT: >>>
CRITICAL HONESTY (Last Boss challenges accepted):
- Published TST nodes are plans only (VAL platform and ROO Origin).
- execution_status for published nodes: blocked_on_tooling (runners catalogued, not pinned in app repo).
- evidence_status: none. EVD node count: 0.
- Zero evidences edges. Zero done claims.
- verifies fields / graph edges are plan lineage — not execution proof.
- Soft greens / coverage alone are NOT pass criteria.
- Tip next: TST-ROO-261. SSOT publishes 258 plans (VAL 124, ROO 134). TST-ROO-248 and TST-ROO-250 are not minted in SSOT. Ragnarok 3 plans live in verification/ro3_tests.sdoc. Nothing is executed. No EVD.

Open must gaps (Auth): REQ-VAL-008, REQ-VAL-015, REQ-VAL-017
Open must live-Discord (Tenant): REQ-VAL-026, REQ-VAL-029, REQ-VAL-030

Poison: Requirements/Requirements.md is NOT SoT.
SoT: Develop@a8a1edd713d6db6db61d42ed4eacf6a9e8737d07.
SSOT sync 2026-10-10 (JST): graph 91; source xWhiteSpace/ROOGuildApp@f38e1378c7cca457fbf8de8e8355d59994f77fc8. Published in SSOT ≠ proven; no EVD; every TST is execution_status blocked_on_tooling, evidence_status none.
<<<

[[/SECTION]]

[[SECTION]]
TITLE: Open must & deferred gaps

[TEXT]
STATEMENT: >>>
### Platform/Auth open must
- GAP-AUTH-TST-001: REQ-VAL-015 [must/open] — REQ-VAL-015 localhost Vite proxy (empty backend base)
- GAP-AUTH-TST-002: REQ-VAL-017 [must/open] — REQ-VAL-017 exhaustive CORS host matrix
- GAP-AUTH-TST-004: REQ-VAL-008 [must/open] — Production Discord token exchange live Vercel FRONTEND_URL oauth bridge (REQ-VAL-008)

### Tenant/Workspace live Discord / open
- GAP-TENANT-TST-001: priority=None coverage=watch_deferred topic=GAP-TENANT-TST-001
- GAP-TENANT-TST-002: priority=must coverage=open topic=GAP-TENANT-TST-002
- GAP-TENANT-TST-003: priority=None coverage=None topic=GAP-TENANT-TST-003
- GAP-TENANT-TST-004: priority=None coverage=None topic=GAP-TENANT-TST-004
- GAP-TENANT-TST-005: priority=None coverage=None topic=GAP-TENANT-TST-005

### Games catalog gaps
- GAP-GAMES-TST-001: priority=None coverage=watch_deferred topic=
- GAP-GAMES-TST-002: priority=None coverage=deferred topic=
- GAP-GAMES-TST-003: priority=None coverage=open topic=
<<<

[[/SECTION]]

[[SECTION]]
TITLE: Platform/Auth — TST-VAL-001 .. TST-VAL-022 (22 plans)

[REQUIREMENT]
UID: TST-VAL-001
STATUS: Active
TITLE: ProcessBootstrap refuses start when required secrets missing
STATEMENT: >>>
Plan: ProcessBootstrap refuses start when required secrets missing
level: unit
verifies: REQ-VAL-002, FNC-VAL-001, UNT-VAL-001, CMP-VAL-001
requires_tol: TOL-ROO-006, TOL-ROO-011
patterns: env_gate_refusal, missing_secret_matrix
execution_status: blocked_on_tooling
evidence_status: none
cases:
  - Missing DISCORD_CLIENT_SECRET refuses normal start: expected=Process does not reach Discord bot init; env gate fails
  - Missing SESSION_SECRET refuses normal start: expected=Refuse start before migrate/bot
  - Missing DATABASE_URL refuses normal start: expected=Refuse start; no half-boot
  - All required secrets present allows gate pass: expected=Env gate succeeds so migrate can run
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD.
ssot_status: published
HONESTY: published plan only; not executed; no EVD.
<<<
RELATIONS:
- TYPE: Parent
  VALUE: REQ-VAL-002

[REQUIREMENT]
UID: TST-VAL-002
STATUS: Active
TITLE: ProcessBootstrap runs migrate before Discord bot start
STATEMENT: >>>
Plan: ProcessBootstrap runs migrate before Discord bot start
level: unit
verifies: REQ-VAL-003, FNC-VAL-001, UNT-VAL-001, CMP-VAL-001
requires_tol: TOL-ROO-006, TOL-ROO-011
patterns: boot_order, migrate_before_bot
execution_status: blocked_on_tooling
evidence_status: none
cases:
  - Successful migrate then bot init order: expected=migrate() completes before Discord bot initialization
  - Migrate failure blocks bot start: expected=Bot never starts when migrate throws/fails
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD.
ssot_status: published
HONESTY: published plan only; not executed; no EVD.
<<<
RELATIONS:
- TYPE: Parent
  VALUE: REQ-VAL-003

[REQUIREMENT]
UID: TST-VAL-003
STATUS: Active
TITLE: HealthProbe maps DB ping success/failure to HTTP outcomes
STATEMENT: >>>
Plan: HealthProbe maps DB ping success/failure to HTTP outcomes
level: unit
verifies: REQ-VAL-001, FNC-VAL-002, API-VAL-001, UNT-VAL-005, CMP-VAL-001
requires_tol: TOL-ROO-006, TOL-ROO-011
patterns: health_probe_unit, db_ping_stub
execution_status: blocked_on_tooling
evidence_status: none
cases:
  - DB ping success → online body: expected=Handler returns online success payload
  - DB ping failure → 503 failure body: expected=Handler returns HTTP 503 semantics with failure body
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD.
ssot_status: published
HONESTY: published plan only; not executed; no EVD.
<<<
RELATIONS:
- TYPE: Parent
  VALUE: REQ-VAL-001

[REQUIREMENT]
UID: TST-VAL-004
STATUS: Active
TITLE: IdentityResolver prefers session then HMAC x-user-profile
STATEMENT: >>>
Plan: IdentityResolver prefers session then HMAC x-user-profile
level: unit
verifies: REQ-VAL-012, FNC-VAL-004, UNT-VAL-010, CMP-VAL-003
requires_tol: TOL-ROO-006, TOL-ROO-011
patterns: identity_resolution, hmac_verify
execution_status: blocked_on_tooling
evidence_status: none
cases:
  - Session user wins over header: expected=Resolved identity is session user when both present
  - Valid HMAC x-user-profile accepted without session: expected=Identity resolved from signed profile using DISCORD_CLIENT_SECRET
  - Invalid/unsigned profile rejected: expected=No authenticated identity
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD.
ssot_status: published
HONESTY: published plan only; not executed; no EVD.
<<<
RELATIONS:
- TYPE: Parent
  VALUE: REQ-VAL-012

[REQUIREMENT]
UID: TST-VAL-005
STATUS: Active
TITLE: ProfileSigner re-signs profile for authenticated /auth/me payload
STATEMENT: >>>
Plan: ProfileSigner re-signs profile for authenticated /auth/me payload
level: unit
verifies: REQ-VAL-010, FNC-VAL-004, UNT-VAL-011, API-VAL-004, CMP-VAL-003
requires_tol: TOL-ROO-006, TOL-ROO-011
patterns: profile_resign, hmac_sign
execution_status: blocked_on_tooling
evidence_status: none
cases:
  - Authenticated me includes re-signed profile: expected=Returned user carries verifiable re-signed profile
  - Unauthenticated me returns authenticated:false: expected=No user / authenticated false
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD.
ssot_status: published
HONESTY: published plan only; not executed; no EVD.
<<<
RELATIONS:
- TYPE: Parent
  VALUE: REQ-VAL-010

[REQUIREMENT]
UID: TST-VAL-006
STATUS: Active
TITLE: SessionCookiePolicy local HTTP vs deployed HTTPS flags
STATEMENT: >>>
Plan: SessionCookiePolicy local HTTP vs deployed HTTPS flags
level: unit
verifies: REQ-VAL-016, FNC-VAL-006, UNT-VAL-003, CMP-VAL-001
requires_tol: TOL-ROO-006, TOL-ROO-011
patterns: cookie_policy_matrix
execution_status: blocked_on_tooling
evidence_status: none
cases:
  - Local HTTP cookie policy: expected=secure:false and sameSite:lax
  - Deployed HTTPS cookie policy: expected=secure:true and sameSite appropriate for cross-site SPA
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD.
ssot_status: published
HONESTY: published plan only; not executed; no EVD.
<<<
RELATIONS:
- TYPE: Parent
  VALUE: REQ-VAL-016

[REQUIREMENT]
UID: TST-VAL-007
STATUS: Active
TITLE: OAuthLoginStart builds Discord authorize URL with scopes and intent
STATEMENT: >>>
Plan: OAuthLoginStart builds Discord authorize URL with scopes and intent
level: unit
verifies: REQ-VAL-004, FNC-VAL-003, API-VAL-002, UNT-VAL-006, CMP-VAL-002
requires_tol: TOL-ROO-006, TOL-ROO-011
patterns: oauth_authorize_url, scope_intent_state
execution_status: blocked_on_tooling
evidence_status: none
cases:
  - Scopes include identify guilds guilds.members.read: expected=Authorize URL carries required scopes
  - State carries signin|signup intent: expected=State encodes intent used by callback routing
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD.
ssot_status: published
HONESTY: published plan only; not executed; no EVD.
<<<
RELATIONS:
- TYPE: Parent
  VALUE: REQ-VAL-004

[REQUIREMENT]
UID: TST-VAL-008
STATUS: Active
TITLE: SessionRestore prefers auth_user query then migrates legacy localStorage key
STATEMENT: >>>
Plan: SessionRestore prefers auth_user query then migrates legacy localStorage key
level: unit
verifies: REQ-VAL-013, FNC-VAL-005, UNT-VAL-013, CMP-VAL-004
requires_tol: TOL-ROO-006, TOL-ROO-011
patterns: spa_session_restore, legacy_key_migrate
execution_status: blocked_on_tooling
evidence_status: none
cases:
  - auth_user query preferred: expected=Restore uses auth_user before localStorage
  - Legacy dynasty_raid_session migrates to guild_raid_session: expected=Legacy key rewritten; session usable
  - Restored session verified via /auth/me path (stubbed): expected=Client treats me verification as auth gate
<<<
COMMENT: >>>
domain: Platform/Auth
notes: TOL-ROO-006 Vitest and TOL-ROO-011 @vitest/coverage-v8 are catalog-published but not installed/pinned in the app repo yet (greenfield). Plan exists; execution_status stays not_run / blocked_on_tooling until Adepts introduce runners. Coverage reports from TOL-ROO-011 are not pass/fail substitutes. evidence_status=none — Last Boss owns EVD. | Gate amend 2026-09-26: stripped non-acceptance USR from verifies (Last Boss C3). | AMEND CHALLENGE: C3 confirmed — USR-VAL-004 absent from unit/integ verifies (Gate already stripped live).
ssot_status: published
HONESTY: published plan only; not executed; no EVD.
<<<
RELATIONS:
- TYPE: Parent
  VALUE: REQ-VAL-013

[REQUIREMENT]
UID: TST-VAL-009
STATUS: Active
TITLE: Platform health seam end-to-end through CMP host + INT-001
STATEMENT: >>>
Plan: Platform health seam end-to-end through CMP host + INT-001
level: integration
verifies: REQ-VAL-001, FNC-VAL-002, API-VAL-001, CMP-VAL-001, INT-VAL-001, UNT-VAL-005
requires_tol: TOL-ROO-006, TOL-ROO-007
patterns: health_seam, db_reachability_integration
execution_status: blocked_on_tooling
evidence_status: none
cases:
  - Reachable DB → GET / online via host seam: expected=INT-VAL-001/API-VAL-001 returns online body
  - Unreachable DB → GET / 503 via host seam: expected=503 failure body through same seam
<<<
COMMENT: >>>
domain: Platform/Auth
notes: Requires TOL-ROO-006 Vitest + TOL-ROO-007 MSW when introduced; neither installed in repo yet. execution_status blocked_on_tooling until Adepts pin. evidence_status=none — Last Boss owns EVD.
ssot_status: published
HONESTY: published plan only; not executed; no EVD.
<<<
RELATIONS:
- TYPE: Parent
  VALUE: REQ-VAL-001

[REQUIREMENT]
UID: TST-VAL-010
STATUS: Active
TITLE: Discord OAuth login+callback seam with mocked Discord token exchange
STATEMENT: >>>
Plan: Discord OAuth login+callback seam with mocked Discord token exchange
level: integration
verifies: REQ-VAL-004, REQ-VAL-005, REQ-VAL-006, REQ-VAL-007, FNC-VAL-003, API-VAL-002, API-VAL-003, CMP-VAL-002, INT-VAL-002, INT-VAL-003, UNT-VAL-006, UNT-VAL-007
requires_tol: TOL-ROO-006, TOL-ROO-007
patterns: oauth_seam_msw, callback_routing_integration
execution_status: blocked_on_tooling
evidence_status: none
cases:
  - Login start redirects to Discord authorize: expected=INT-002 yields Discord redirect with scopes/intent
  - Callback single onboarded guild non-signup → tenant path: expected=Redirect into that tenant path
  - Callback zero/multiple/signup → /select-guild with auth_user: expected=Landing on select-guild with auth context
  - Callback persists compact guild list to session/DB: expected=Guild membership persisted as specified by REQ-005
<<<
COMMENT: >>>
domain: Platform/Auth
notes: Requires TOL-ROO-006 Vitest + TOL-ROO-007 MSW when introduced; neither installed in repo yet. execution_status blocked_on_tooling until Adepts pin. evidence_status=none — Last Boss owns EVD.
ssot_status: published
HONESTY: published plan only; not executed; no EVD.
<<<
RELATIONS:
- TYPE: Parent
  VALUE: REQ-VAL-004

[REQUIREMENT]
UID: TST-VAL-011
STATUS: Active
TITLE: Identity me/logout seam across CMP-003 and INT-004/005
STATEMENT: >>>
Plan: Identity me/logout seam across CMP-003 and INT-004/005
level: integration
verifies: REQ-VAL-010, REQ-VAL-011, FNC-VAL-004, API-VAL-004, API-VAL-005, CMP-VAL-003, INT-VAL-004, INT-VAL-005, UNT-VAL-010, UNT-VAL-011, UNT-VAL-012
requires_tol: TOL-ROO-006, TOL-ROO-007
patterns: session_me_logout_seam
execution_status: blocked_on_tooling
evidence_status: none
cases:
  - Session-backed GET /auth/me authenticated: expected=authenticated:true with re-signed profile
  - POST /auth/logout clears connect.sid: expected=Session destroyed; subsequent me unauthenticated
<<<
COMMENT: >>>
domain: Platform/Auth
notes: Requires TOL-ROO-006 Vitest + TOL-ROO-007 MSW when introduced; neither installed in repo yet. execution_status blocked_on_tooling until Adepts pin. evidence_status=none — Last Boss owns EVD.
ssot_status: published
HONESTY: published plan only; not executed; no EVD.
<<<
RELATIONS:
- TYPE: Parent
  VALUE: REQ-VAL-010

[REQUIREMENT]
UID: TST-VAL-012
STATUS: Active
TITLE: Discord circuit-open guard redirects login/callback to landing
STATEMENT: >>>
Plan: Discord circuit-open guard redirects login/callback to landing
level: integration
verifies: REQ-VAL-009, FNC-VAL-003, CMP-VAL-002, UNT-VAL-009, INT-VAL-002, INT-VAL-003
requires_tol: TOL-ROO-006, TOL-ROO-007
patterns: circuit_breaker_oauth, rate_limit_redirect
execution_status: blocked_on_tooling
evidence_status: none
cases:
  - Open circuit on login → landing with discord_rate_limited: expected=No Discord authorize; landing hint including until
  - Open circuit on callback → landing with discord_rate_limited: expected=OAuth not completed; rate-limit hint
<<<
COMMENT: >>>
domain: Platform/Auth
notes: Requires TOL-ROO-006 Vitest + TOL-ROO-007 MSW when introduced; neither installed in repo yet. execution_status blocked_on_tooling until Adepts pin. evidence_status=none — Last Boss owns EVD.
ssot_status: published
HONESTY: published plan only; not executed; no EVD.
<<<
RELATIONS:
- TYPE: Parent
  VALUE: REQ-VAL-009

[REQUIREMENT]
UID: TST-VAL-013
STATUS: Active
TITLE: SPA CredentialedApiClient attaches credentials and auth headers (MSW)
STATEMENT: >>>
Plan: SPA CredentialedApiClient attaches credentials and auth headers (MSW)
level: integration
verifies: REQ-VAL-014, FNC-VAL-005, CMP-VAL-004, UNT-VAL-014
requires_tol: TOL-ROO-006, TOL-ROO-007
patterns: credentialed_fetch_msw, header_attachment
execution_status: blocked_on_tooling
evidence_status: none
cases:
  - apiFetch uses credentials:include: expected=Outgoing request includes credentials
  - Attaches x-user-profile and x-tenant-id when available: expected=Headers present on authenticated client calls
<<<
COMMENT: >>>
domain: Platform/Auth
notes: Requires TOL-ROO-006 Vitest + TOL-ROO-007 MSW when introduced; neither installed in repo yet. execution_status blocked_on_tooling until Adepts pin. evidence_status=none — Last Boss owns EVD. | Gate amend 2026-09-26: stripped non-acceptance USR from verifies (Last Boss C3). | AMEND CHALLENGE: C3 confirmed — USR-VAL-004 absent from unit/integ verifies (Gate already stripped live).
ssot_status: published
HONESTY: published plan only; not executed; no EVD.
<<<
RELATIONS:
- TYPE: Parent
  VALUE: REQ-VAL-014

[REQUIREMENT]
UID: TST-VAL-014
STATUS: Active
TITLE: GET / health probe HTTP contract (online vs 503)
STATEMENT: >>>
Plan: GET / health probe HTTP contract (online vs 503)
level: system
verifies: REQ-VAL-001, FNC-VAL-002, API-VAL-001
requires_tol: TOL-ROO-006, TOL-ROO-005
patterns: http_health_contract
execution_status: blocked_on_tooling
evidence_status: none
cases:
  - GET / 200 online when DB ping succeeds: expected=Online success body per API-VAL-001
  - GET / 503 when DB ping fails: expected=Failure body; not false-online
<<<
COMMENT: >>>
domain: Platform/Auth
notes: HTTP/API system plans; runner likely Vitest (TOL-ROO-006) against Express app (TOL-ROO-005) when introduced. Not installed yet → not_run / blocked_on_tooling. evidence_status=none — Last Boss owns EVD.
ssot_status: published
HONESTY: published plan only; not executed; no EVD.
<<<
RELATIONS:
- TYPE: Parent
  VALUE: REQ-VAL-001

[REQUIREMENT]
UID: TST-VAL-015
STATUS: Active
TITLE: GET /auth/login Discord OAuth start HTTP contract
STATEMENT: >>>
Plan: GET /auth/login Discord OAuth start HTTP contract
level: system
verifies: REQ-VAL-004, REQ-VAL-009, FNC-VAL-003, API-VAL-002
requires_tol: TOL-ROO-006, TOL-ROO-005
patterns: http_oauth_login
execution_status: blocked_on_tooling
evidence_status: none
cases:
  - GET /auth/login redirects to Discord with scopes+intent: expected=3xx to Discord authorize URL
  - Open circuit path yields landing rate-limit redirect: expected=Landing with discord_rate_limited when circuit open
<<<
COMMENT: >>>
domain: Platform/Auth
notes: HTTP/API system plans; runner likely Vitest (TOL-ROO-006) against Express app (TOL-ROO-005) when introduced. Not installed yet → not_run / blocked_on_tooling. evidence_status=none — Last Boss owns EVD.
ssot_status: published
HONESTY: published plan only; not executed; no EVD.
<<<
RELATIONS:
- TYPE: Parent
  VALUE: REQ-VAL-004

[REQUIREMENT]
UID: TST-VAL-016
STATUS: Active
TITLE: GET /auth/callback exchange, persist, and post-auth routing HTTP
STATEMENT: >>>
Plan: GET /auth/callback exchange, persist, and post-auth routing HTTP
level: system
verifies: REQ-VAL-005, REQ-VAL-006, REQ-VAL-007, FNC-VAL-003, API-VAL-003
requires_tol: TOL-ROO-006, TOL-ROO-005, TOL-ROO-007
patterns: http_oauth_callback, post_auth_routing
execution_status: blocked_on_tooling
evidence_status: none
cases:
  - Successful exchange persists guild list and session identity: expected=Session established; compact guild list stored
  - Single-guild non-signup → tenant redirect: expected=Redirect into tenant path
  - Zero/multi/signup → /select-guild?auth_user: expected=Select-guild with auth_user context
  - Production exchange config-path probe (FRONTEND_URL oauth bridge wiring) — NOT REQ-008 closure: expected=Config selects FRONTEND_URL bridge path when production flags set; does NOT prove live Vercel bridge E2E. REQ-VAL-008 remains open (GAP-AUTH-TST-004).
<<<
COMMENT: >>>
domain: Platform/Auth
notes: HTTP/API system plans; runner likely Vitest (TOL-ROO-006) against Express app (TOL-ROO-005) when introduced. Not installed yet → not_run / blocked_on_tooling. evidence_status=none — Last Boss owns EVD. | AMEND CHALLENGE C5: REQ-VAL-008 removed from verifies. Config-path case alone does NOT satisfy must REQ-008 (live Vercel FRONTEND_URL oauth exchange bridge). Coverage = open via GAP-AUTH-TST-004. Do not count REQ-008 covered.
ssot_status: published
HONESTY: published plan only; not executed; no EVD.
<<<
RELATIONS:
- TYPE: Parent
  VALUE: REQ-VAL-005

[REQUIREMENT]
UID: TST-VAL-017
STATUS: Active
TITLE: GET /auth/me and POST /auth/logout HTTP contracts
STATEMENT: >>>
Plan: GET /auth/me and POST /auth/logout HTTP contracts
level: system
verifies: REQ-VAL-010, REQ-VAL-011, REQ-VAL-012, FNC-VAL-004, API-VAL-004, API-VAL-005
requires_tol: TOL-ROO-006, TOL-ROO-005
patterns: http_me_logout
execution_status: blocked_on_tooling
evidence_status: none
cases:
  - Authenticated GET /auth/me: expected={authenticated:true,user} with re-signed profile
  - Unauthenticated GET /auth/me: expected=authenticated:false
  - POST /auth/logout clears session cookie: expected=connect.sid cleared; follow-up me unauthenticated
<<<
COMMENT: >>>
domain: Platform/Auth
notes: HTTP/API system plans; runner likely Vitest (TOL-ROO-006) against Express app (TOL-ROO-005) when introduced. Not installed yet → not_run / blocked_on_tooling. evidence_status=none — Last Boss owns EVD.
ssot_status: published
HONESTY: published plan only; not executed; no EVD.
<<<
RELATIONS:
- TYPE: Parent
  VALUE: REQ-VAL-010

[REQUIREMENT]
UID: TST-VAL-018
STATUS: Active
TITLE: Acceptance: platform health and safe boot visible to operators
STATEMENT: >>>
Plan: Acceptance: platform health and safe boot visible to operators
level: acceptance
verifies: USR-VAL-001, REQ-VAL-001, REQ-VAL-002, REQ-VAL-003, FNC-VAL-001, FNC-VAL-002, API-VAL-001
requires_tol: TOL-ROO-005, TOL-ROO-006, TOL-ROO-008
patterns: acceptance_boot_health, operator_probe, acceptance_boot_health_playwright, operator_observable_ui
execution_status: blocked_on_tooling
evidence_status: none
cases:
  - Deployed/process with secrets up → health online: expected=GET / reflects online when DB reachable
  - Missing required secret refuses start (operator-observable): expected=Process does not serve false-online
  - Playwright: operator opens health/status surface and observes online when process healthy: expected=Browser-visible health indicator or documented operator URL shows online; no false-online
  - Playwright: operator-observable refusal when required secrets missing (no false-online UI/API): expected=Operator cannot observe healthy/online serving when boot gate refused; failure visible
<<<
COMMENT: >>>
domain: Platform/Auth
notes: Acceptance for USR-VAL-001. HTTP probe cases use TOL-ROO-005/006; operator-observable UI/browser cases require TOL-ROO-008 Playwright (catalog-only, not pinned → blocked_on_tooling). AMEND CHALLENGE C4: added Playwright path for operator-visible acceptance while retaining USR-001 claim. evidence_status=none — Last Boss owns EVD. Never self-certify done. published≠proven.
ssot_status: published
HONESTY: published plan only; not executed; no EVD.
<<<
RELATIONS:
- TYPE: Parent
  VALUE: REQ-VAL-001

[REQUIREMENT]
UID: TST-VAL-019
STATUS: Active
TITLE: Acceptance: Discord OAuth sign-in routes to tenant or select-guild
STATEMENT: >>>
Plan: Acceptance: Discord OAuth sign-in routes to tenant or select-guild
level: acceptance
verifies: USR-VAL-002, REQ-VAL-004, REQ-VAL-005, REQ-VAL-006, REQ-VAL-007, FNC-VAL-003, API-VAL-002, API-VAL-003
requires_tol: TOL-ROO-008
patterns: acceptance_oauth_browser, post_login_path
execution_status: blocked_on_tooling
evidence_status: none
cases:
  - User starts login from SPA and completes Discord OAuth (staged/mock IdP as available): expected=Session established; lands on tenant or /select-guild per guild count/intent
  - Signup intent forces select-guild even with one guild: expected=/select-guild with auth_user
<<<
COMMENT: >>>
domain: Platform/Auth
notes: UI/browser acceptance needs TOL-ROO-008 Playwright when introduced; API-only acceptance may use HTTP client without browser. Playwright not installed → blocked_on_tooling for browser cases. evidence_status=none — Last Boss owns EVD. Never self-certify done.
ssot_status: published
HONESTY: published plan only; not executed; no EVD.
<<<
RELATIONS:
- TYPE: Parent
  VALUE: REQ-VAL-004

[REQUIREMENT]
UID: TST-VAL-020
STATUS: Active
TITLE: Acceptance: session identity via /auth/me and logout clears cookie
STATEMENT: >>>
Plan: Acceptance: session identity via /auth/me and logout clears cookie
level: acceptance
verifies: USR-VAL-003, REQ-VAL-010, REQ-VAL-011, FNC-VAL-004, API-VAL-004, API-VAL-005
requires_tol: TOL-ROO-008
patterns: acceptance_session_logout_browser
execution_status: blocked_on_tooling
evidence_status: none
cases:
  - Authenticated SPA sees me identity: expected=UI/API client observes authenticated user
  - Logout returns to unauthenticated state: expected=Cookie cleared; protected shell no longer authenticated
<<<
COMMENT: >>>
domain: Platform/Auth
notes: UI/browser acceptance needs TOL-ROO-008 Playwright when introduced; API-only acceptance may use HTTP client without browser. Playwright not installed → blocked_on_tooling for browser cases. evidence_status=none — Last Boss owns EVD. Never self-certify done.
ssot_status: published
HONESTY: published plan only; not executed; no EVD.
<<<
RELATIONS:
- TYPE: Parent
  VALUE: REQ-VAL-010

[REQUIREMENT]
UID: TST-VAL-021
STATUS: Active
TITLE: Acceptance: SPA session restore and credentialed API after OAuth redirect
STATEMENT: >>>
Plan: Acceptance: SPA session restore and credentialed API after OAuth redirect
level: acceptance
verifies: USR-VAL-004, REQ-VAL-013, REQ-VAL-014, FNC-VAL-005
requires_tol: TOL-ROO-008, TOL-ROO-007
patterns: acceptance_spa_restore
execution_status: blocked_on_tooling
evidence_status: none
cases:
  - auth_user query restore after OAuth redirect: expected=SPA restores session and verifies via /auth/me
  - Subsequent API calls send credentials + profile/tenant headers: expected=Credentialed client behavior observed in browser network
<<<
COMMENT: >>>
domain: Platform/Auth
notes: UI/browser acceptance needs TOL-ROO-008 Playwright when introduced; API-only acceptance may use HTTP client without browser. Playwright not installed → blocked_on_tooling for browser cases. evidence_status=none — Last Boss owns EVD. Never self-certify done.
ssot_status: published
HONESTY: published plan only; not executed; no EVD.
<<<
RELATIONS:
- TYPE: Parent
  VALUE: REQ-VAL-013

[REQUIREMENT]
UID: TST-VAL-022
STATUS: Active
TITLE: Acceptance: unauthenticated shell gate and /login→/landing
STATEMENT: >>>
Plan: Acceptance: unauthenticated shell gate and /login→/landing
level: acceptance
verifies: USR-VAL-005, REQ-VAL-019, REQ-VAL-020, FNC-VAL-006, UNT-VAL-015, CMP-VAL-004
requires_tol: TOL-ROO-008
patterns: acceptance_unauth_routing
execution_status: blocked_on_tooling
evidence_status: none
cases:
  - /login permanently redirects to /landing: expected=Browser ends on /landing
  - Unauthenticated navigation to protected shell → /landing: expected=Redirect to landing; no protected content
<<<
COMMENT: >>>
domain: Platform/Auth
notes: UI/browser acceptance needs TOL-ROO-008 Playwright when introduced; API-only acceptance may use HTTP client without browser. Playwright not installed → blocked_on_tooling for browser cases. evidence_status=none — Last Boss owns EVD. Never self-certify done.
ssot_status: published
HONESTY: published plan only; not executed; no EVD.
<<<
RELATIONS:
- TYPE: Parent
  VALUE: REQ-VAL-019

[[/SECTION]]

[[SECTION]]
TITLE: Tenant/Workspace — TST-VAL-023 .. TST-VAL-045, TST-VAL-260 (24 plans)

[REQUIREMENT]
UID: TST-VAL-023
STATUS: Active
TITLE: TenantIdentityKey treats Discord guild id as tenants.id PK
STATEMENT: >>>
Plan: TenantIdentityKey treats Discord guild id as tenants.id PK
level: unit
verifies: REQ-VAL-021, FNC-VAL-007, UNT-VAL-018, CMP-VAL-005
requires_tol: TOL-ROO-006, TOL-ROO-011
patterns: tenant_pk_guild_id, identity_key_equality
execution_status: blocked_on_tooling
evidence_status: none
cases:
  - Guild id string becomes tenants.id: expected=Created/looked-up tenant PK equals Discord guild id
  - Non-guild synthetic id refused as tenant PK: expected=Identity helper rejects or does not mint non-guild PK
  - Round-trip: load by guild id returns same tenant: expected=Lookup by guild id hits the same row as create
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-021

[REQUIREMENT]
UID: TST-VAL-024
STATUS: Active
TITLE: MineAndOnboardableDiscovery lists onboarded and capacity-gated onboardable
STATEMENT: >>>
Plan: MineAndOnboardableDiscovery lists onboarded and capacity-gated onboardable
level: unit
verifies: REQ-VAL-022, REQ-VAL-023, FNC-VAL-008, UNT-VAL-019, CMP-VAL-005
requires_tol: TOL-ROO-006, TOL-ROO-011
patterns: mine_list, capacity_empty_onboardable
execution_status: blocked_on_tooling
evidence_status: none
cases:
  - Visible onboarded tenants returned for member: expected=mine includes onboarded guilds user can see
  - Manage-Server guilds appear as onboardable when capacity allows: expected=onboardable includes Manage-Server guilds under capacity
  - Capacity full → onboardable empty + billing capacity flags: expected=onboardable=[], capacity flags present per REQ-023
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. Deep billing entitlement math deferred to Billing/Capacity domain. | AMEND C-T3: REQ-023 planned surface lineage only (empty onboardable + capacity flags). Deep billing entitlement math deferred to Billing/Capacity (GAP-TENANT-TST-001). Never imply REQ-023 fully proven via Tenant alone. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-022

[REQUIREMENT]
UID: TST-VAL-025
STATUS: Active
TITLE: TenantSelectAndRosterSync builds session and upserts auction member
STATEMENT: >>>
Plan: TenantSelectAndRosterSync builds session and upserts auction member
level: unit
verifies: REQ-VAL-024, REQ-VAL-025, FNC-VAL-009, UNT-VAL-020, CMP-VAL-005
requires_tol: TOL-ROO-006, TOL-ROO-011
patterns: tenant_select, roster_member_upsert
execution_status: blocked_on_tooling
evidence_status: none
cases:
  - Select requires membership visibility: expected=Non-visible tenant select refused
  - Select builds session user with officer flag and enabled games: expected=Session carries officer/enabledGames/subscription slice
  - Select upserts auction/members/{discordId} displayName/roles/syncedAt: expected=Member doc upserted with displayName, roles, syncedAt
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-024

[REQUIREMENT]
UID: TST-VAL-026
STATUS: Active
TITLE: WorkspaceOnboard gates Manage Server, bot presence, officer roles; 409/bot_not_in_guild
STATEMENT: >>>
Plan: WorkspaceOnboard gates Manage Server, bot presence, officer roles; 409/bot_not_in_guild
level: unit
verifies: REQ-VAL-026, REQ-VAL-027, REQ-VAL-028, REQ-VAL-029, REQ-VAL-033, FNC-VAL-010, UNT-VAL-021, CMP-VAL-005
requires_tol: TOL-ROO-006, TOL-ROO-011
patterns: onboard_gates, onboard_409, bot_not_in_guild
execution_status: blocked_on_tooling
evidence_status: none
cases:
  - Happy path: Manage Server + bot in guild + ≥1 officer role → create tenant: expected=Tenant+settings created; empty Discord channel map; onboarded=true
  - Already onboarded → 409: expected=Reject with already-onboarded conflict
  - Bot not in guild → bot_not_in_guild + invite URL: expected=Reject payload includes invite URL
  - Missing officer role names refused: expected=Onboard does not create without ≥1 officer role name
  - Manage Server required for create (not day-to-day officer tools): expected=Create gate checks Manage Server/owner; officer tools not substituted
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T2: MSW/system/acceptance plans keep verifies lineage only. Live Discord guild onboard E2E (bot invite/token) for REQ-026/029/030 (+ USR-008 / TST-043) remains open / never_soft_pass (GAP-TENANT-TST-002). MSW ≠ live Discord proof; never soft-pass. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-026

[REQUIREMENT]
UID: TST-VAL-027
STATUS: Active
TITLE: BotInviteUrlProvider returns Discord bot invite URL
STATEMENT: >>>
Plan: BotInviteUrlProvider returns Discord bot invite URL
level: unit
verifies: REQ-VAL-030, FNC-VAL-011, UNT-VAL-022, CMP-VAL-005
requires_tol: TOL-ROO-006, TOL-ROO-011
patterns: bot_invite_url
execution_status: blocked_on_tooling
evidence_status: none
cases:
  - Invite URL generated without guildId: expected=Valid Discord bot invite URL returned
  - Optional guildId query included when provided: expected=Invite URL embeds guildId when supplied
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T2: MSW/system/acceptance plans keep verifies lineage only. Live Discord guild onboard E2E (bot invite/token) for REQ-026/029/030 (+ USR-008 / TST-043) remains open / never_soft_pass (GAP-TENANT-TST-002). MSW ≠ live Discord proof; never soft-pass. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-030

[REQUIREMENT]
UID: TST-VAL-028
STATUS: Active
TITLE: DiscordRoleCatalog requires bot in guild and sorts non-@everyone roles
STATEMENT: >>>
Plan: DiscordRoleCatalog requires bot in guild and sorts non-@everyone roles
level: unit
verifies: REQ-VAL-031, FNC-VAL-011, UNT-VAL-023, CMP-VAL-005
requires_tol: TOL-ROO-006, TOL-ROO-011
patterns: discord_role_catalog, bot_presence_gate
execution_status: blocked_on_tooling
evidence_status: none
cases:
  - Bot in guild → non-@everyone roles sorted by position: expected=Catalog excludes @everyone; ordered by position
  - Bot not in guild → refuse catalog: expected=Error/empty refusal when bot missing
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-031

[REQUIREMENT]
UID: TST-VAL-029
STATUS: Active
TITLE: OfficerPredicate owner OR adminRoles; empty adminRoles → owner only
STATEMENT: >>>
Plan: OfficerPredicate owner OR adminRoles; empty adminRoles → owner only
level: unit
verifies: REQ-VAL-032, REQ-VAL-033, FNC-VAL-012, UNT-VAL-026, CMP-VAL-006
requires_tol: TOL-ROO-006, TOL-ROO-011
patterns: officer_predicate, admin_roles_casefold
execution_status: blocked_on_tooling
evidence_status: none
cases:
  - Tenant owner always officer: expected=owner_discord_id matches → officer true
  - adminRoles name/id match case-insensitive → officer: expected=Role name/id in adminRoles grants officer
  - Empty adminRoles → owner only: expected=Non-owner with empty adminRoles is not officer
  - Manage Server alone does not grant day-to-day officer tools: expected=Predicate does not treat Manage Server as officer for tools
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-032

[REQUIREMENT]
UID: TST-VAL-030
STATUS: Active
TITLE: WorkspaceSettingsService officer-only read/update display/timezone/adminRoles
STATEMENT: >>>
Plan: WorkspaceSettingsService officer-only read/update display/timezone/adminRoles
level: unit
verifies: REQ-VAL-034, FNC-VAL-013, UNT-VAL-024, CMP-VAL-005
requires_tol: TOL-ROO-006, TOL-ROO-011
patterns: workspace_settings, officer_only_settings
execution_status: blocked_on_tooling
evidence_status: none
cases:
  - Officer can read display name, timezone, adminRoles + Discord roles: expected=Read returns settings slice and role catalog
  - Officer can update display/timezone/adminRoles: expected=Update persists fields
  - Non-officer refused: expected=Read/update denied for non-officer
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-034

[REQUIREMENT]
UID: TST-VAL-031
STATUS: Active
TITLE: GuildLogoManager upload ≤512KB, clear, Discord icon fallback
STATEMENT: >>>
Plan: GuildLogoManager upload ≤512KB, clear, Discord icon fallback
level: unit
verifies: REQ-VAL-035, REQ-VAL-036, FNC-VAL-014, UNT-VAL-025, CMP-VAL-005
requires_tol: TOL-ROO-006, TOL-ROO-011
patterns: guild_logo_upload, logo_size_gate, discord_icon_fallback
execution_status: blocked_on_tooling
evidence_status: none
cases:
  - Upload ≤512KB succeeds: expected=Custom logo stored
  - Upload >512KB refused: expected=Reject oversized payload
  - Clear removes custom logo: expected=DELETE clears stored custom logo
  - No custom logo → effective logo falls back to Discord guild icon: expected=Effective logo URL/path uses Discord icon
<<<
COMMENT: >>>
domain: Tenant/Workspace
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = plan lineage only (published ≠ proven). No depends_on authored. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-035

[REQUIREMENT]
UID: TST-VAL-032
STATUS: Active
TITLE: Tenants mine discovery seam through CMP-005 + INT-006
STATEMENT: >>>
Plan: Tenants mine discovery seam through CMP-005 + INT-006
level: integration
verifies: REQ-VAL-022, REQ-VAL-023, FNC-VAL-008, API-VAL-006, CMP-VAL-005, INT-VAL-006, UNT-VAL-019
requires_tol: TOL-ROO-006, TOL-ROO-007
patterns: seam_tenants_mine, msw_discord_guilds
execution_status: blocked_on_tooling
evidence_status: none
cases:
  - Authenticated mine lists onboarded + onboardable: expected=INT-006 returns combined list for session user
  - Capacity-full path empties onboardable with flags: expected=Seam surfaces empty onboardable + capacity flags
  - Unauthenticated mine refused: expected=Session guard fails closed
<<<
COMMENT: >>>
domain: Tenant/Workspace
notes: TOL-ROO-006 Vitest + TOL-ROO-007 MSW are catalog-published but not installed/pinned (greenfield). Seam plans use MSW for Discord/HTTP mocks. execution_status=blocked_on_tooling. evidence_status=none — Last Boss owns EVD. verifies = plan lineage only. No depends_on. | AMEND C-T3: REQ-023 planned surface lineage only (empty onboardable + capacity flags). Deep billing entitlement math deferred to Billing/Capacity (GAP-TENANT-TST-001). Never imply REQ-023 fully proven via Tenant alone. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-022

[REQUIREMENT]
UID: TST-VAL-033
STATUS: Active
TITLE: Tenant select seam builds session and syncs roster member
STATEMENT: >>>
Plan: Tenant select seam builds session and syncs roster member
level: integration
verifies: REQ-VAL-024, REQ-VAL-025, FNC-VAL-009, API-VAL-007, CMP-VAL-005, INT-VAL-007, UNT-VAL-020
requires_tol: TOL-ROO-006, TOL-ROO-007
patterns: seam_tenant_select, roster_sync_seam
execution_status: blocked_on_tooling
evidence_status: none
cases:
  - Select visible tenant → session currentTenantId set: expected=Session reflects selected tenant + officer/games slice
  - Select upserts auction member doc: expected=Member upsert observed via seam/mock store
  - Select invisible tenant refused: expected=Visibility gate fails closed
<<<
COMMENT: >>>
domain: Tenant/Workspace
notes: TOL-ROO-006 Vitest + TOL-ROO-007 MSW are catalog-published but not installed/pinned (greenfield). Seam plans use MSW for Discord/HTTP mocks. execution_status=blocked_on_tooling. evidence_status=none — Last Boss owns EVD. verifies = plan lineage only. No depends_on. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-024

[REQUIREMENT]
UID: TST-VAL-034
STATUS: Active
TITLE: Tenant onboard seam happy path, 409, and bot_not_in_guild
STATEMENT: >>>
Plan: Tenant onboard seam happy path, 409, and bot_not_in_guild
level: integration
verifies: REQ-VAL-026, REQ-VAL-027, REQ-VAL-028, REQ-VAL-029, REQ-VAL-033, FNC-VAL-010, API-VAL-008, CMP-VAL-005, INT-VAL-008, UNT-VAL-021
requires_tol: TOL-ROO-006, TOL-ROO-007
patterns: seam_tenant_onboard, onboard_conflict, bot_invite_on_miss
execution_status: blocked_on_tooling
evidence_status: none
cases:
  - Manage Server + bot present + officer roles → onboard creates tenant: expected=INT-008 creates tenant/settings; onboarded=true
  - Already onboarded → 409 through seam: expected=Conflict status propagated
  - Bot missing → bot_not_in_guild with invite URL: expected=Error payload includes invite URL
<<<
COMMENT: >>>
domain: Tenant/Workspace
notes: TOL-ROO-006 Vitest + TOL-ROO-007 MSW are catalog-published but not installed/pinned (greenfield). Seam plans use MSW for Discord/HTTP mocks. execution_status=blocked_on_tooling. evidence_status=none — Last Boss owns EVD. verifies = plan lineage only. No depends_on. | AMEND C-T2: MSW/system/acceptance plans keep verifies lineage only. Live Discord guild onboard E2E (bot invite/token) for REQ-026/029/030 (+ USR-008 / TST-043) remains open / never_soft_pass (GAP-TENANT-TST-002). MSW ≠ live Discord proof; never soft-pass. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-026

[REQUIREMENT]
UID: TST-VAL-035
STATUS: Active
TITLE: Invite URL and Discord roles catalog seams
STATEMENT: >>>
Plan: Invite URL and Discord roles catalog seams
level: integration
verifies: REQ-VAL-030, REQ-VAL-031, FNC-VAL-011, API-VAL-009, API-VAL-010, CMP-VAL-005, INT-VAL-009, INT-VAL-010, UNT-VAL-022, UNT-VAL-023
requires_tol: TOL-ROO-006, TOL-ROO-007
patterns: seam_invite_url, seam_discord_roles
execution_status: blocked_on_tooling
evidence_status: none
cases:
  - Invite-url seam returns bot invite (optional guildId): expected=INT-009 yields invite URL
  - Discord-roles seam requires bot; returns sorted non-@everyone: expected=INT-010 catalog correct when bot present
  - Discord-roles seam refuses when bot absent: expected=Fails closed
<<<
COMMENT: >>>
domain: Tenant/Workspace
notes: TOL-ROO-006 Vitest + TOL-ROO-007 MSW are catalog-published but not installed/pinned (greenfield). Seam plans use MSW for Discord/HTTP mocks. execution_status=blocked_on_tooling. evidence_status=none — Last Boss owns EVD. verifies = plan lineage only. No depends_on. | AMEND C-T2: MSW/system/acceptance plans keep verifies lineage only. Live Discord guild onboard E2E (bot invite/token) for REQ-026/029/030 (+ USR-008 / TST-043) remains open / never_soft_pass (GAP-TENANT-TST-002). MSW ≠ live Discord proof; never soft-pass. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-030

[REQUIREMENT]
UID: TST-VAL-036
STATUS: Active
TITLE: Workspace settings and logo seams officer-gated via CMP-006
STATEMENT: >>>
Plan: Workspace settings and logo seams officer-gated via CMP-006
level: integration
verifies: REQ-VAL-032, REQ-VAL-034, REQ-VAL-035, REQ-VAL-036, FNC-VAL-012, FNC-VAL-013, FNC-VAL-014, API-VAL-011, API-VAL-012, API-VAL-013, API-VAL-014, CMP-VAL-005, CMP-VAL-006, INT-VAL-011, INT-VAL-012, INT-VAL-013, INT-VAL-014, UNT-VAL-024, UNT-VAL-025, UNT-VAL-026
requires_tol: TOL-ROO-006, TOL-ROO-007
patterns: seam_workspace_settings, seam_guild_logo, officer_gate_integ
execution_status: blocked_on_tooling
evidence_status: none
cases:
  - Officer GET/POST workspace settings succeed: expected=INT-011/012 persist/read display/timezone/adminRoles
  - Non-officer workspace settings refused: expected=CMP-006 officer gate fails closed
  - Officer logo upload ≤512KB and clear: expected=INT-013/014 store and clear custom logo
  - Effective logo falls back to Discord icon when cleared: expected=Fallback path observed after clear
<<<
COMMENT: >>>
domain: Tenant/Workspace
notes: TOL-ROO-006 Vitest + TOL-ROO-007 MSW are catalog-published but not installed/pinned (greenfield). Seam plans use MSW for Discord/HTTP mocks. execution_status=blocked_on_tooling. evidence_status=none — Last Boss owns EVD. verifies = plan lineage only. No depends_on. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-032

[REQUIREMENT]
UID: TST-VAL-037
STATUS: Active
TITLE: GET /api/tenants/mine and POST /api/tenants/select HTTP contracts
STATEMENT: >>>
Plan: GET /api/tenants/mine and POST /api/tenants/select HTTP contracts
level: system
verifies: REQ-VAL-022, REQ-VAL-023, REQ-VAL-024, REQ-VAL-025, FNC-VAL-008, FNC-VAL-009, API-VAL-006, API-VAL-007
requires_tol: TOL-ROO-005, TOL-ROO-006, TOL-ROO-007
patterns: http_tenants_mine, http_tenants_select
execution_status: blocked_on_tooling
evidence_status: none
cases:
  - GET /api/tenants/mine session → 200 with onboarded/onboardable: expected=Contract shape matches inventory
  - GET /api/tenants/mine capacity-full → empty onboardable + flags: expected=REQ-023 flags present
  - POST /api/tenants/select visible tenant → session built: expected=200 and session currentTenantId set
  - POST /api/tenants/select without session → refuse: expected=Auth guard fails closed
<<<
COMMENT: >>>
domain: Tenant/Workspace
notes: HTTP contract plans cite TOL-ROO-005 Express host + TOL-ROO-006 Vitest (+ TOL-ROO-007 MSW where Discord is mocked). Runners not pinned → blocked_on_tooling. evidence_status=none. verifies = plan lineage only. No depends_on. | AMEND C-T3: REQ-023 planned surface lineage only (empty onboardable + capacity flags). Deep billing entitlement math deferred to Billing/Capacity (GAP-TENANT-TST-001). Never imply REQ-023 fully proven via Tenant alone. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-022

[REQUIREMENT]
UID: TST-VAL-038
STATUS: Active
TITLE: POST /api/tenants/onboard HTTP contract (create, 409, bot_not_in_guild)
STATEMENT: >>>
Plan: POST /api/tenants/onboard HTTP contract (create, 409, bot_not_in_guild)
level: system
verifies: REQ-VAL-026, REQ-VAL-027, REQ-VAL-028, REQ-VAL-029, REQ-VAL-033, FNC-VAL-010, API-VAL-008
requires_tol: TOL-ROO-005, TOL-ROO-006, TOL-ROO-007
patterns: http_tenants_onboard
execution_status: blocked_on_tooling
evidence_status: none
cases:
  - POST onboard happy path → 2xx + tenant created: expected=Tenant+settings; onboarded=true
  - POST onboard already exists → 409: expected=Conflict status
  - POST onboard bot missing → bot_not_in_guild + invite URL: expected=Error body includes invite URL
  - POST onboard without Manage Server → refuse: expected=session_manage_server guard fails closed
<<<
COMMENT: >>>
domain: Tenant/Workspace
notes: HTTP contract plans cite TOL-ROO-005 Express host + TOL-ROO-006 Vitest (+ TOL-ROO-007 MSW where Discord is mocked). Runners not pinned → blocked_on_tooling. evidence_status=none. verifies = plan lineage only. No depends_on. | AMEND C-T2: MSW/system/acceptance plans keep verifies lineage only. Live Discord guild onboard E2E (bot invite/token) for REQ-026/029/030 (+ USR-008 / TST-043) remains open / never_soft_pass (GAP-TENANT-TST-002). MSW ≠ live Discord proof; never soft-pass. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-026

[REQUIREMENT]
UID: TST-VAL-039
STATUS: Active
TITLE: GET /api/tenants/invite-url and GET /api/tenants/discord-roles HTTP contracts
STATEMENT: >>>
Plan: GET /api/tenants/invite-url and GET /api/tenants/discord-roles HTTP contracts
level: system
verifies: REQ-VAL-030, REQ-VAL-031, FNC-VAL-011, API-VAL-009, API-VAL-010
requires_tol: TOL-ROO-005, TOL-ROO-006, TOL-ROO-007
patterns: http_invite_url, http_discord_roles
execution_status: blocked_on_tooling
evidence_status: none
cases:
  - GET invite-url (no auth) returns bot invite URL: expected=200 with invite URL; optional guildId honored
  - GET discord-roles with session + bot present: expected=Sorted non-@everyone roles
  - GET discord-roles bot absent → refuse: expected=Fails closed
<<<
COMMENT: >>>
domain: Tenant/Workspace
notes: HTTP contract plans cite TOL-ROO-005 Express host + TOL-ROO-006 Vitest (+ TOL-ROO-007 MSW where Discord is mocked). Runners not pinned → blocked_on_tooling. evidence_status=none. verifies = plan lineage only. No depends_on. | AMEND C-T2: MSW/system/acceptance plans keep verifies lineage only. Live Discord guild onboard E2E (bot invite/token) for REQ-026/029/030 (+ USR-008 / TST-043) remains open / never_soft_pass (GAP-TENANT-TST-002). MSW ≠ live Discord proof; never soft-pass. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-030

[REQUIREMENT]
UID: TST-VAL-040
STATUS: Active
TITLE: Workspace GET/POST and logo POST/DELETE HTTP contracts (officer-only)
STATEMENT: >>>
Plan: Workspace GET/POST and logo POST/DELETE HTTP contracts (officer-only)
level: system
verifies: REQ-VAL-034, REQ-VAL-035, REQ-VAL-036, FNC-VAL-013, FNC-VAL-014, API-VAL-011, API-VAL-012, API-VAL-013, API-VAL-014
requires_tol: TOL-ROO-005, TOL-ROO-006, TOL-ROO-007
patterns: http_workspace_settings, http_guild_logo
execution_status: blocked_on_tooling
evidence_status: none
cases:
  - GET/POST /api/tenants/workspace as officer: expected=Read/update display/timezone/adminRoles
  - GET/POST workspace as non-officer → refuse: expected=session_officer guard fails closed
  - POST /api/tenants/logo ≤512KB; DELETE clears: expected=Upload/clear succeed for officer
  - POST logo >512KB → refuse: expected=Size gate fails closed
<<<
COMMENT: >>>
domain: Tenant/Workspace
notes: HTTP contract plans cite TOL-ROO-005 Express host + TOL-ROO-006 Vitest (+ TOL-ROO-007 MSW where Discord is mocked). Runners not pinned → blocked_on_tooling. evidence_status=none. verifies = plan lineage only. No depends_on. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-034

[REQUIREMENT]
UID: TST-VAL-041
STATUS: Active
TITLE: Acceptance: tenant identity is Discord guild (one guild = one tenant PK)
STATEMENT: >>>
Plan: Acceptance: tenant identity is Discord guild (one guild = one tenant PK)
level: acceptance
verifies: USR-VAL-006, REQ-VAL-021, FNC-VAL-007, CMP-VAL-005, UNT-VAL-018
requires_tol: TOL-ROO-008, TOL-ROO-006
patterns: acceptance_tenant_identity, guild_equals_tenant
execution_status: blocked_on_tooling
evidence_status: none
cases:
  - Operator/onboard sees tenant keyed by Discord guild id: expected=UI/API tenant id matches guild id
  - No alternate tenant PK invented for guild: expected=One guild maps to one tenants.id
<<<
COMMENT: >>>
domain: Tenant/Workspace
notes: Acceptance plans cite TOL-ROO-008 Playwright (and TOL-ROO-007 MSW where Discord is mocked). Catalog-only greenfield → blocked_on_tooling. USR allowed only because level=acceptance. evidence_status=none — Last Boss owns EVD. verifies = plan lineage only; published ≠ proven. No depends_on. No EVD/evidences. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-021

[REQUIREMENT]
UID: TST-VAL-042
STATUS: Active
TITLE: Acceptance: members discover and select workspace
STATEMENT: >>>
Plan: Acceptance: members discover and select workspace
level: acceptance
verifies: USR-VAL-007, REQ-VAL-022, REQ-VAL-023, REQ-VAL-024, REQ-VAL-025, FNC-VAL-008, FNC-VAL-009, API-VAL-006, API-VAL-007, CMP-VAL-005
requires_tol: TOL-ROO-008, TOL-ROO-007
patterns: acceptance_discover_select, select_guild_flow
execution_status: blocked_on_tooling
evidence_status: none
cases:
  - Member opens select-guild and sees onboarded + onboardable: expected=List visible in UI
  - Capacity full shows empty onboardable / capacity messaging: expected=User-visible empty onboardable path
  - Selecting a workspace builds session and lands in tenant context: expected=Post-select session has currentTenantId
<<<
COMMENT: >>>
domain: Tenant/Workspace
notes: Acceptance plans cite TOL-ROO-008 Playwright (and TOL-ROO-007 MSW where Discord is mocked). Catalog-only greenfield → blocked_on_tooling. USR allowed only because level=acceptance. evidence_status=none — Last Boss owns EVD. verifies = plan lineage only; published ≠ proven. No depends_on. No EVD/evidences. | AMEND C-T3: REQ-023 planned surface lineage only (empty onboardable + capacity flags). Deep billing entitlement math deferred to Billing/Capacity (GAP-TENANT-TST-001). Never imply REQ-023 fully proven via Tenant alone. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-022

[REQUIREMENT]
UID: TST-VAL-043
STATUS: Active
TITLE: Acceptance: guild owner onboards new Discord guild workspace
STATEMENT: >>>
Plan: Acceptance: guild owner onboards new Discord guild workspace
level: acceptance
verifies: USR-VAL-008, REQ-VAL-026, REQ-VAL-027, REQ-VAL-028, REQ-VAL-029, REQ-VAL-030, REQ-VAL-031, REQ-VAL-033, FNC-VAL-010, FNC-VAL-011, API-VAL-008, API-VAL-009, API-VAL-010, CMP-VAL-005
requires_tol: TOL-ROO-008, TOL-ROO-007
patterns: acceptance_onboard, bot_invite_ux
execution_status: blocked_on_tooling
evidence_status: none
cases:
  - Owner with Manage Server onboards when bot present and officer roles set: expected=Workspace created; onboarded=true
  - Already onboarded guild shows conflict (409 UX): expected=User sees already-onboarded messaging
  - Bot missing offers invite URL path: expected=User can obtain invite URL and retry
<<<
COMMENT: >>>
domain: Tenant/Workspace
notes: Acceptance plans cite TOL-ROO-008 Playwright (and TOL-ROO-007 MSW where Discord is mocked). Catalog-only greenfield → blocked_on_tooling. USR allowed only because level=acceptance. evidence_status=none — Last Boss owns EVD. verifies = plan lineage only; published ≠ proven. No depends_on. No EVD/evidences. Live Discord guild E2E with real bot invite may remain env-blocked; MSW path is plan-primary until Adepts pin runners + Discord test fixtures. | AMEND C-T2: MSW/system/acceptance plans keep verifies lineage only. Live Discord guild onboard E2E (bot invite/token) for REQ-026/029/030 (+ USR-008 / TST-043) remains open / never_soft_pass (GAP-TENANT-TST-002). MSW ≠ live Discord proof; never soft-pass. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-026

[REQUIREMENT]
UID: TST-VAL-044
STATUS: Active
TITLE: Acceptance: officers manage officer model and workspace settings including logo
STATEMENT: >>>
Plan: Acceptance: officers manage officer model and workspace settings including logo
level: acceptance
verifies: USR-VAL-009, REQ-VAL-032, REQ-VAL-033, REQ-VAL-034, REQ-VAL-035, REQ-VAL-036, FNC-VAL-012, FNC-VAL-013, FNC-VAL-014, API-VAL-011, API-VAL-012, API-VAL-013, API-VAL-014, CMP-VAL-005, CMP-VAL-006
requires_tol: TOL-ROO-008, TOL-ROO-007
patterns: acceptance_officer_settings, acceptance_guild_logo
execution_status: blocked_on_tooling
evidence_status: none
cases:
  - Officer edits display name, timezone, adminRoles: expected=Settings persist and reload
  - Non-officer cannot open day-to-day officer tools: expected=UI/API refuse; Manage Server alone insufficient
  - Officer uploads ≤512KB logo and can clear; Discord icon fallback visible: expected=Logo UX matches REQ-035/036
<<<
COMMENT: >>>
domain: Tenant/Workspace
notes: Acceptance plans cite TOL-ROO-008 Playwright (and TOL-ROO-007 MSW where Discord is mocked). Catalog-only greenfield → blocked_on_tooling. USR allowed only because level=acceptance. evidence_status=none — Last Boss owns EVD. verifies = plan lineage only; published ≠ proven. No depends_on. No EVD/evidences. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-032

[REQUIREMENT]
UID: TST-VAL-045
STATUS: Active
TITLE: Acceptance: authenticated user forced to select-guild and ordered post-login path
STATEMENT: >>>
Plan: Acceptance: authenticated user forced to select-guild and ordered post-login path
level: acceptance
verifies: USR-VAL-010, REQ-VAL-037, REQ-VAL-038, FNC-VAL-015, CMP-VAL-004, UNT-VAL-017
requires_tol: TOL-ROO-008, TOL-ROO-007
patterns: acceptance_post_login_routing, force_select_guild
execution_status: blocked_on_tooling
evidence_status: none
cases:
  - Authenticated user without currentTenantId forced to /select-guild: expected=SPA routes to select-guild
  - Post-login path order: select-guild → billing → choose games → game setup → game home: expected=Resolver follows ordered steps per REQ-038
<<<
COMMENT: >>>
domain: Tenant/Workspace
notes: Acceptance plans cite TOL-ROO-008 Playwright (and TOL-ROO-007 MSW where Discord is mocked). Catalog-only greenfield → blocked_on_tooling. USR allowed only because level=acceptance. evidence_status=none — Last Boss owns EVD. verifies = plan lineage only; published ≠ proven. No depends_on. No EVD/evidences. FNC-015 allocated to SPA Shell CMP-004; unit coverage lives on Auth UNT-VAL-017 (no second Tenant PostLoginPathResolver). Cross-domain verifies to CMP-004/UNT-017 intentional. | AMEND C-T1/C-T4: verifies = planned lineage only; published≠proven; coverage (TOL-011) ≠ pass/fail; zero EVD/evidences; never claim covered/done while blocked_on_tooling.
ssot_status: published
HONESTY: published plan only; not executed; no EVD.
<<<
RELATIONS:
- TYPE: Parent
  VALUE: REQ-VAL-037

[REQUIREMENT]
UID: TST-VAL-260
STATUS: Active
TITLE: LoginRosterUpsertOriginOnly writes the sign-in roster entry only for Origin and never for Ragnarok 3
STATEMENT: >>>
Plan: LoginRosterUpsertOriginOnly writes the sign-in roster entry only for Origin and never for Ragnarok 3
level: unit
verifies: REQ-VAL-209, FNC-ROO-211, UNT-ROO-222, CMP-VAL-005
requires_tol: TOL-ROO-006
patterns: login_roster_origin_only
execution_status: blocked_on_tooling
evidence_status: none
cases:
  - Origin not enabled skips the roster write: expected=no roster entry created or updated in any game
  - Origin enabled upserts the Origin entry: expected=auction/members/{uid} upserted inside runWithGame('ragnarok-origin')
  - No Ragnarok 3 entry is written at sign-in: expected=the Ragnarok 3 roster is unchanged
<<<
COMMENT: >>>
domain: Tenant/Workspace
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Ragnarok 3 counterpart, text only: UNT-RO3-029 (the Ragnarok 3 roster follows Discord sync, not sign-in).
ssot_status: published
HONESTY: published plan only; not executed; no EVD.
<<<
RELATIONS:
- TYPE: Parent
  VALUE: REQ-VAL-209

[[/SECTION]]

[[SECTION]]
TITLE: Games catalog — TST-VAL-046 .. TST-VAL-065, TST-VAL-251 .. TST-VAL-253, TST-VAL-258 .. TST-VAL-259 (25 plans)

[REQUIREMENT]
UID: TST-VAL-046
STATUS: Active
TITLE: GamesWhitelist accepts adventurer-guild, ragnarok-origin, and ragnarok-3
STATEMENT: >>>
Plan: GamesWhitelist accepts adventurer-guild, ragnarok-origin, and ragnarok-3
level: unit
verifies: REQ-VAL-039, REQ-R3-001, FNC-VAL-016, UNT-VAL-027, CMP-VAL-007
requires_tol: TOL-ROO-006, TOL-ROO-011
patterns: known_game_ids, parse_enabled_games_filter, r3_path_catalog
execution_status: blocked_on_tooling
evidence_status: none
cases:
  - KNOWN_GAME_IDS includes adventurer-guild, ragnarok-origin, and ragnarok-3: expected=Whitelist equals the three catalog ids
  - isKnownGame rejects unknown id: expected=Unknown gameId → false / validation refuse
  - parseEnabledGames drops unknown stored ids: expected=Stored junk filtered; only known ids remain
  - R3 has no setupPath and gameIdForPath matches /games/ragnarok-3 first: expected=setupPathForGame(R3) → /games/ragnarok-3; Origin root paths still Origin
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling.
ssot_status: published
HONESTY: published plan only; not executed; no EVD.
<<<
RELATIONS:
- TYPE: Parent
  VALUE: REQ-VAL-039

[REQUIREMENT]
UID: TST-VAL-047
STATUS: Active
TITLE: EnableKnownGame appends known id with active seat and setupPath
STATEMENT: >>>
Plan: EnableKnownGame appends known id with active seat and setupPath
level: unit
verifies: REQ-VAL-040, FNC-VAL-017, UNT-VAL-028, CMP-VAL-007
requires_tol: TOL-ROO-006, TOL-ROO-011
patterns: enable_known_game, setup_path_for_game, active_seat_gate_surface
execution_status: blocked_on_tooling
evidence_status: none
cases:
  - Officer + active seat appends known gameId idempotently: expected=enabled_games gains id once; re-enable no duplicate
  - RO enable returns setupPath /games/ragnarok-origin/setup: expected=setupPathForGame(RO) → RO setup route
  - AG enable returns AG home path (no setup route): expected=setupPathForGame(AG) → /games/adventurer-guild
  - Inactive seat → payment_required surface: expected=Gate refuses with 402-shaped payment_required (seat predicate mocked; deep Billing deferred)
  - Unknown gameId refused: expected=Validation error; list unchanged
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling. | Active-seat predicate is planned_surface via mocked tenantHasAccess only (GAP-GAMES-TST-001). Deep Billing entitlement deferred — never imply REQ-050 proven via Games.
ssot_status: published
HONESTY: published plan only; not executed; no EVD.
<<<
RELATIONS:
- TYPE: Parent
  VALUE: REQ-VAL-040

[REQUIREMENT]
UID: TST-VAL-048
STATUS: Active
TITLE: DisableGamePreserveData removes enabled id without wiping stores
STATEMENT: >>>
Plan: DisableGamePreserveData removes enabled id without wiping stores
level: unit
verifies: REQ-VAL-041, FNC-VAL-018, UNT-VAL-029, CMP-VAL-007
requires_tol: TOL-ROO-006, TOL-ROO-011
patterns: disable_game_preserve_data, enabled_games_remove
execution_status: blocked_on_tooling
evidence_status: none
cases:
  - Officer removes known gameId from enabled_games: expected=Id absent from enabled list after disable
  - Stored game documents / channel map retained: expected=json_docs and discord channel map not deleted
  - Unknown gameId → 400-shaped validation: expected=Refuse unknown; no side effects
  - Active seat not required for disable: expected=Disable succeeds for officer without active seat
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling.
ssot_status: published
HONESTY: published plan only; not executed; no EVD.
<<<
RELATIONS:
- TYPE: Parent
  VALUE: REQ-VAL-041

[REQUIREMENT]
UID: TST-VAL-049
STATUS: Active
TITLE: RoSetupCompleteness requires aucreq OR auction OR warAnnounce
STATEMENT: >>>
Plan: RoSetupCompleteness requires aucreq OR auction OR warAnnounce
level: unit
verifies: REQ-VAL-042, FNC-VAL-019, UNT-VAL-030, CMP-VAL-007
requires_tol: TOL-ROO-006, TOL-ROO-011
patterns: ro_setup_completeness, channel_or_gate
execution_status: blocked_on_tooling
evidence_status: none
cases:
  - All three channel ids empty → RO incomplete: expected=isRagnarokSetupComplete false
  - Any one of aucreq/auction/warAnnounce set → complete: expected=Completeness true for each single-id case
  - gameSetupMap marks RO complete only when enabled AND complete: expected=Enabled+incomplete stays incomplete in map
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling.
ssot_status: published
HONESTY: published plan only; not executed; no EVD.
<<<
RELATIONS:
- TYPE: Parent
  VALUE: REQ-VAL-042

[REQUIREMENT]
UID: TST-VAL-050
STATUS: Active
TITLE: AgNoSetupReadiness marks AG ready on enable alone
STATEMENT: >>>
Plan: AgNoSetupReadiness marks AG ready on enable alone
level: unit
verifies: REQ-VAL-043, FNC-VAL-020, UNT-VAL-031, CMP-VAL-007
requires_tol: TOL-ROO-006, TOL-ROO-011
patterns: ag_no_setup, game_setup_paths_absent
execution_status: blocked_on_tooling
evidence_status: none
cases:
  - GAME_SETUP_PATHS has no adventurer-guild entry: expected=No dedicated AG setup route
  - Enabled AG alone → gameSetupMap ready: expected=AG true in map solely from enabledGames
  - No channel ids required for AG: expected=AG readiness ignores Discord channel map
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling.
ssot_status: published
HONESTY: published plan only; not executed; no EVD.
<<<
RELATIONS:
- TYPE: Parent
  VALUE: REQ-VAL-043

[REQUIREMENT]
UID: TST-VAL-051
STATUS: Active
TITLE: RoChannelMapPersistence writes war rooms 1–5 and channel fields
STATEMENT: >>>
Plan: RoChannelMapPersistence writes war rooms 1–5 and channel fields
level: unit
verifies: REQ-VAL-044, FNC-VAL-021, UNT-VAL-032, CMP-VAL-007
requires_tol: TOL-ROO-006, TOL-ROO-011
patterns: ro_channel_map, war_rooms_1_5, active_seat_gate_surface
execution_status: blocked_on_tooling
evidence_status: none
cases:
  - Persists auction/aucreq/genroom/attendance/warAnnounce/raidScreenshot: expected=discordChannels fields written as provided
  - Persists warRooms DISCORD_WARROOM_ID_1..5: expected=War rooms 1–5 stored
  - RO not enabled → game_required refuse: expected=403-shaped game_required when RO absent from enabled_games
  - Inactive seat → payment_required surface: expected=402-shaped refuse with mocked seat false (Billing deep deferred)
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling. | Active-seat predicate planned_surface only (GAP-GAMES-TST-001). Channel ids are stored snowflakes — no live Discord bot E2E required for this unit plan.
ssot_status: published
HONESTY: published plan only; not executed; no EVD.
<<<
RELATIONS:
- TYPE: Parent
  VALUE: REQ-VAL-044

[REQUIREMENT]
UID: TST-VAL-052
STATUS: Active
TITLE: RequireGameGate returns 403 game_required for RO and AG mounts
STATEMENT: >>>
Plan: RequireGameGate returns 403 game_required for RO and AG mounts
level: unit
verifies: REQ-VAL-045, REQ-VAL-046, FNC-VAL-022, UNT-VAL-033, CMP-VAL-008
requires_tol: TOL-ROO-006, TOL-ROO-011
patterns: require_game_gate, game_required_403, tenant_required_409
execution_status: blocked_on_tooling
evidence_status: none
cases:
  - RO mount without ragnarok-origin → 403 game_required: expected=Body includes code game_required and gameId ragnarok-origin
  - AG mount without adventurer-guild → 403 game_required: expected=Body includes code game_required and gameId adventurer-guild
  - Enabled game passes requireGame: expected=Gate allows when id in parseEnabledGames
  - No current tenant → 409 tenant_required: expected=Missing tenant context fails closed
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling.
ssot_status: published
HONESTY: published plan only; not executed; no EVD.
<<<
RELATIONS:
- TYPE: Parent
  VALUE: REQ-VAL-045

[REQUIREMENT]
UID: TST-VAL-053
STATUS: Active
TITLE: SpaGamePathGate redirects disabled paths and persists valhalla_active_game
STATEMENT: >>>
Plan: SpaGamePathGate redirects disabled paths and persists valhalla_active_game
level: unit
verifies: REQ-VAL-047, REQ-VAL-048, FNC-VAL-023, UNT-VAL-035, CMP-VAL-004
requires_tol: TOL-ROO-006, TOL-ROO-011
patterns: spa_game_path_gate, valhalla_active_game, post_login_redirect
execution_status: blocked_on_tooling
evidence_status: none
cases:
  - Navigate into disabled game path → redirect postLoginPath: expected=Blocked path does not render; Navigate to resolver result
  - workspace/games/billing paths exempt from game gate: expected=Exempt paths not redirected by pathGameId check
  - Active game id written to localStorage valhalla_active_game: expected=Key valhalla_active_game holds active id
  - Stored activeGameId not in enabledGames → reconcile to first enabled: expected=Stale id replaced when an enabled game exists
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling.
ssot_status: published
HONESTY: published plan only; not executed; no EVD.
<<<
RELATIONS:
- TYPE: Parent
  VALUE: REQ-VAL-047

[REQUIREMENT]
UID: TST-VAL-054
STATUS: Active
TITLE: Enable-game seam INT-015 through CMP-007
STATEMENT: >>>
Plan: Enable-game seam INT-015 through CMP-007
level: integration
verifies: REQ-VAL-040, FNC-VAL-017, API-VAL-015, CMP-VAL-007, INT-VAL-015, UNT-VAL-028
requires_tol: TOL-ROO-006, TOL-ROO-007
patterns: seam_enable_game, msw_session_officer_seat
execution_status: blocked_on_tooling
evidence_status: none
cases:
  - Officer + active seat enable known game via INT-015: expected=Seam returns enabledGames + setupPath; CMP-007 provider
  - Non-officer enable refused: expected=403 fail-closed at seam
  - Inactive seat → payment_required at seam: expected=402-shaped surface (mocked seat; Billing deep deferred)
<<<
COMMENT: >>>
domain: Games catalog
notes: TOL-ROO-006 Vitest + TOL-ROO-007 MSW are catalog-published but not installed/pinned (greenfield). execution_status=blocked_on_tooling. evidence_status=none — Last Boss owns EVD. verifies = planned lineage only (published ≠ proven). No depends_on. No EVD/evidences. C-T1: planned verifies lineage only — never say covered while blocked. | GAP-GAMES-TST-001: seat surface only.
ssot_status: published
HONESTY: published plan only; not executed; no EVD.
<<<
RELATIONS:
- TYPE: Parent
  VALUE: REQ-VAL-040

[REQUIREMENT]
UID: TST-VAL-055
STATUS: Active
TITLE: Disable-game seam INT-016 preserves stored game data
STATEMENT: >>>
Plan: Disable-game seam INT-016 preserves stored game data
level: integration
verifies: REQ-VAL-041, FNC-VAL-018, API-VAL-016, CMP-VAL-007, INT-VAL-016, UNT-VAL-029
requires_tol: TOL-ROO-006, TOL-ROO-007
patterns: seam_disable_game, preserve_game_stores
execution_status: blocked_on_tooling
evidence_status: none
cases:
  - Officer disable removes enabled id via INT-016: expected=enabledGames updated; success body
  - After disable, channel map / game docs still readable: expected=Stores retained across seam
  - Unknown gameId refused at seam: expected=400-shaped validation
<<<
COMMENT: >>>
domain: Games catalog
notes: TOL-ROO-006 Vitest + TOL-ROO-007 MSW are catalog-published but not installed/pinned (greenfield). execution_status=blocked_on_tooling. evidence_status=none — Last Boss owns EVD. verifies = planned lineage only (published ≠ proven). No depends_on. No EVD/evidences. C-T1: planned verifies lineage only — never say covered while blocked.
ssot_status: published
HONESTY: published plan only; not executed; no EVD.
<<<
RELATIONS:
- TYPE: Parent
  VALUE: REQ-VAL-041

[REQUIREMENT]
UID: TST-VAL-056
STATUS: Active
TITLE: RO game-setup seam INT-017 persists channel map including war rooms
STATEMENT: >>>
Plan: RO game-setup seam INT-017 persists channel map including war rooms
level: integration
verifies: REQ-VAL-044, FNC-VAL-021, API-VAL-017, CMP-VAL-007, INT-VAL-017, UNT-VAL-032
requires_tol: TOL-ROO-006, TOL-ROO-007
patterns: seam_game_setup, war_rooms_persist, msw_session_ro_enabled
execution_status: blocked_on_tooling
evidence_status: none
cases:
  - Officer + RO enabled + seat persists full channel map via INT-017: expected=discordChannels + warRooms 1–5 stored
  - RO not enabled → game_required at seam: expected=403 game_required
  - Inactive seat → payment_required surface: expected=402-shaped (Billing deep deferred)
<<<
COMMENT: >>>
domain: Games catalog
notes: TOL-ROO-006 Vitest + TOL-ROO-007 MSW are catalog-published but not installed/pinned (greenfield). execution_status=blocked_on_tooling. evidence_status=none — Last Boss owns EVD. verifies = planned lineage only (published ≠ proven). No depends_on. No EVD/evidences. C-T1: planned verifies lineage only — never say covered while blocked. | Channel ids are snowflake strings under test — no live Discord bot invite required for planned MSW lineage. GAP-GAMES-TST-001 seat surface.
ssot_status: published
HONESTY: published plan only; not executed; no EVD.
<<<
RELATIONS:
- TYPE: Parent
  VALUE: REQ-VAL-044

[REQUIREMENT]
UID: TST-VAL-057
STATUS: Active
TITLE: RequireGame mount/API-tree wiring under CMP-008 for RO and AG
STATEMENT: >>>
Plan: RequireGame mount/API-tree wiring under CMP-008 for RO and AG
level: unit
verifies: REQ-VAL-045, REQ-VAL-046, FNC-VAL-022, CMP-VAL-008, UNT-VAL-033
requires_tol: TOL-ROO-006, TOL-ROO-011
patterns: unit_require_game_mount_tree, ro_ag_mount_gate
execution_status: blocked_on_tooling
evidence_status: none
cases:
  - RO API tree without RO enabled → 403 game_required: expected=Mount middleware under CMP-008 enforces FNC-022 (unit mount-tree)
  - AG API tree without AG enabled → 403 game_required: expected=AG mount enforces requireGame(adventurer-guild) under CMP-008
  - Enabled game allows mount through gate: expected=Request proceeds past requireGame on mount tree
  - Missing tenant → 409 tenant_required: expected=Fail closed at mount wiring
<<<
COMMENT: >>>
domain: Games catalog
notes: TOL-ROO-006 Vitest and TOL-ROO-011 @vitest/coverage-v8 are catalog-published but not installed/pinned in the app repo yet (greenfield). Plan exists; execution_status stays blocked_on_tooling until Adepts introduce runners. Coverage reports from TOL-ROO-011 are not pass/fail substitutes. evidence_status=none — Last Boss owns EVD. verifies = planned lineage only (published ≠ proven). No depends_on authored. C-T1: never claim covered/done while blocked_on_tooling. | AMEND C-G1: demoted level=unit — was false integration (no INT-* for requireGame in SSOT; INT-015/016/017 are enable/disable/setup only). Do not invent private INT. Cases retained as unit mount/API-tree under UNT-033/CMP-008. Differentiated from TST-VAL-052 (gate predicate/body unit) — 057 focuses on mount-tree wiring cases under CMP-008. Same verifies set retained; merge/supersede not required — keep ID. No System Designer INT route needed.
ssot_status: published
HONESTY: published plan only; not executed; no EVD.
<<<
RELATIONS:
- TYPE: Parent
  VALUE: REQ-VAL-045

[REQUIREMENT]
UID: TST-VAL-058
STATUS: Active
TITLE: POST /api/tenants/enable-game HTTP contract
STATEMENT: >>>
Plan: POST /api/tenants/enable-game HTTP contract
level: system
verifies: REQ-VAL-040, FNC-VAL-017, API-VAL-015
requires_tol: TOL-ROO-005, TOL-ROO-006, TOL-ROO-007
patterns: http_enable_game, api_015_contract
execution_status: blocked_on_tooling
evidence_status: none
cases:
  - POST enable-game officer+seat+known id → 200 enabledGames+setupPath+user: expected=Contract matches API-VAL-015 success shape
  - Unauthenticated → 401: expected=Auth guard fails closed
  - No tenant → 409 tenant_required: expected=Error code tenant_required
  - Inactive seat → 402 payment_required: expected=Surface payment_required (seat mocked)
  - Unknown game → 400: expected=Validation refuse
  - Non-officer → 403: expected=Officer guard fails closed
<<<
COMMENT: >>>
domain: Games catalog
notes: HTTP/system plans cite TOL-ROO-005 Express host + TOL-ROO-006 Vitest (+ TOL-ROO-007 MSW where session/tenant mocked). Runners not pinned → blocked_on_tooling. evidence_status=none. verifies = planned lineage only; published ≠ proven. No depends_on. No EVD/evidences. C-T1: never claim covered/done while blocked_on_tooling. | GAP-GAMES-TST-001: 402 seat path is planned_surface only.
ssot_status: published
HONESTY: published plan only; not executed; no EVD.
<<<
RELATIONS:
- TYPE: Parent
  VALUE: REQ-VAL-040

[REQUIREMENT]
UID: TST-VAL-059
STATUS: Active
TITLE: POST /api/tenants/disable-game HTTP contract
STATEMENT: >>>
Plan: POST /api/tenants/disable-game HTTP contract
level: system
verifies: REQ-VAL-041, FNC-VAL-018, API-VAL-016
requires_tol: TOL-ROO-005, TOL-ROO-006, TOL-ROO-007
patterns: http_disable_game, api_016_contract
execution_status: blocked_on_tooling
evidence_status: none
cases:
  - POST disable-game officer+known id → 200 enabledGames without id: expected=Contract matches API-VAL-016; data retained
  - Unauthenticated → 401: expected=Auth fail closed
  - No tenant → 409 tenant_required: expected=Error code tenant_required
  - Unknown game → 400: expected=Validation refuse
  - Non-officer → 403: expected=Officer guard fails closed
<<<
COMMENT: >>>
domain: Games catalog
notes: HTTP/system plans cite TOL-ROO-005 Express host + TOL-ROO-006 Vitest (+ TOL-ROO-007 MSW where session/tenant mocked). Runners not pinned → blocked_on_tooling. evidence_status=none. verifies = planned lineage only; published ≠ proven. No depends_on. No EVD/evidences. C-T1: never claim covered/done while blocked_on_tooling.
ssot_status: published
HONESTY: published plan only; not executed; no EVD.
<<<
RELATIONS:
- TYPE: Parent
  VALUE: REQ-VAL-041

[REQUIREMENT]
UID: TST-VAL-060
STATUS: Active
TITLE: POST /api/tenants/game-setup HTTP contract
STATEMENT: >>>
Plan: POST /api/tenants/game-setup HTTP contract
level: system
verifies: REQ-VAL-044, FNC-VAL-021, API-VAL-017
requires_tol: TOL-ROO-005, TOL-ROO-006, TOL-ROO-007
patterns: http_game_setup, api_017_contract
execution_status: blocked_on_tooling
evidence_status: none
cases:
  - POST game-setup officer+RO+seat+channels → 200 user: expected=Contract matches API-VAL-017; war rooms 1–5 accepted
  - RO not enabled → 403 game_required: expected=Error code game_required
  - Inactive seat → 402 payment_required: expected=Surface payment_required (seat mocked)
  - Non-officer → 403: expected=Officer guard fails closed
  - No tenant → 409 tenant_required: expected=Error code tenant_required
<<<
COMMENT: >>>
domain: Games catalog
notes: HTTP/system plans cite TOL-ROO-005 Express host + TOL-ROO-006 Vitest (+ TOL-ROO-007 MSW where session/tenant mocked). Runners not pinned → blocked_on_tooling. evidence_status=none. verifies = planned lineage only; published ≠ proven. No depends_on. No EVD/evidences. C-T1: never claim covered/done while blocked_on_tooling. | GAP-GAMES-TST-001 seat surface. No live Discord bot required for HTTP contract plan (snowflake body).
ssot_status: published
HONESTY: published plan only; not executed; no EVD.
<<<
RELATIONS:
- TYPE: Parent
  VALUE: REQ-VAL-044

[REQUIREMENT]
UID: TST-VAL-061
STATUS: Active
TITLE: Mounted RO/AG APIs enforce requireGame HTTP 403 game_required
STATEMENT: >>>
Plan: Mounted RO/AG APIs enforce requireGame HTTP 403 game_required
level: system
verifies: REQ-VAL-045, REQ-VAL-046, FNC-VAL-022, API-ROO-031, API-ROO-108
requires_tol: TOL-ROO-005, TOL-ROO-006, TOL-ROO-007
patterns: http_require_game_mounts, game_required_system, api_031_108_sample
execution_status: blocked_on_tooling
evidence_status: none
cases:
  - Sample RO mount GET /api/requests/init (API-ROO-031) without RO → 403 game_required: expected=code game_required, gameId ragnarok-origin
  - Sample AG mount GET /api/adventurer-guild/highlights (API-ROO-108) without AG → 403 game_required: expected=code game_required, gameId adventurer-guild
  - Enabled game allows mount past gate: expected=Not 403 game_required when enabled
  - No tenant on mount → 409 tenant_required: expected=Error code tenant_required
<<<
COMMENT: >>>
domain: Games catalog
notes: HTTP/system plans cite TOL-ROO-005 Express host + TOL-ROO-006 Vitest (+ TOL-ROO-007 MSW where session/tenant mocked). Runners not pinned → blocked_on_tooling. evidence_status=none. verifies = planned lineage only; published ≠ proven. No depends_on. No EVD/evidences. C-T1: never claim covered/done while blocked_on_tooling. | AMEND C-G2: added representative API verifies API-ROO-031 (/api/requests/init) + API-ROO-108 (/api/adventurer-guild/highlights) matching sister 058–060 pattern (each system plan cites concrete API). planned_surface: samples only — full RO /api/requests tree API-031..047 and AG API-108..114 not each cited; incomplete mount set.
ssot_status: published
HONESTY: published plan only; not executed; no EVD.
<<<
RELATIONS:
- TYPE: Parent
  VALUE: REQ-VAL-045

[REQUIREMENT]
UID: TST-VAL-062
STATUS: Active
TITLE: Acceptance: officers enable/disable known games without data loss
STATEMENT: >>>
Plan: Acceptance: officers enable/disable known games without data loss
level: acceptance
verifies: USR-VAL-011, REQ-VAL-039, REQ-VAL-040, REQ-VAL-041, FNC-VAL-016, FNC-VAL-017, FNC-VAL-018, CMP-VAL-007, UNT-VAL-027, UNT-VAL-028, UNT-VAL-029
requires_tol: TOL-ROO-008, TOL-ROO-007
patterns: accept_enable_disable, known_games_only
execution_status: blocked_on_tooling
evidence_status: none
cases:
  - Officer with seat enables ragnarok-origin and sees setup path: expected=UI/API reflects enabled RO + setup entry
  - Officer enables adventurer-guild without setup step: expected=AG ready on enable; no channel setup required
  - Officer disables a game; prior game data still present: expected=Enabled list drops id; stored data retained
  - Unknown game cannot be enabled: expected=Catalog whitelist refuses
<<<
COMMENT: >>>
domain: Games catalog
notes: Acceptance plans cite TOL-ROO-008 Playwright (and TOL-ROO-007 MSW where HTTP/session mocked). Catalog-only greenfield → blocked_on_tooling. USR allowed only because level=acceptance. evidence_status=none — Last Boss owns EVD. verifies = planned lineage only; published ≠ proven. No depends_on. No EVD/evidences. C-T1: never claim covered/done while blocked_on_tooling. | GAP-GAMES-TST-001: seat precondition mocked/plan-surface; deep Billing watch/deferred.
ssot_status: published
HONESTY: published plan only; not executed; no EVD.
<<<
RELATIONS:
- TYPE: Parent
  VALUE: REQ-VAL-039

[REQUIREMENT]
UID: TST-VAL-063
STATUS: Active
TITLE: Acceptance: RO channel setup completeness and game-setup persistence
STATEMENT: >>>
Plan: Acceptance: RO channel setup completeness and game-setup persistence
level: acceptance
verifies: USR-VAL-012, REQ-VAL-042, REQ-VAL-043, REQ-VAL-044, FNC-VAL-019, FNC-VAL-020, FNC-VAL-021, CMP-VAL-007, UNT-VAL-030, UNT-VAL-031, UNT-VAL-032
requires_tol: TOL-ROO-008, TOL-ROO-007
patterns: accept_ro_setup, ag_no_setup, war_rooms
execution_status: blocked_on_tooling
evidence_status: none
cases:
  - RO remains incomplete until aucreq/auction/warAnnounce mapped: expected=Setup incomplete UX until one channel set
  - Officer persists RO channel map including war rooms 1–5: expected=game-setup saves map; completeness can flip
  - AG has no setup path after enable: expected=No AG channel-setup route required
<<<
COMMENT: >>>
domain: Games catalog
notes: Acceptance plans cite TOL-ROO-008 Playwright (and TOL-ROO-007 MSW where HTTP/session mocked). Catalog-only greenfield → blocked_on_tooling. USR allowed only because level=acceptance. evidence_status=none — Last Boss owns EVD. verifies = planned lineage only; published ≠ proven. No depends_on. No EVD/evidences. C-T1: never claim covered/done while blocked_on_tooling. | Channel map persistence plans use mocked session/HTTP; live Discord bot invite not required for Games catalog acceptance of stored snowflakes. GAP-GAMES-TST-001 seat surface on game-setup.
ssot_status: published
HONESTY: published plan only; not executed; no EVD.
<<<
RELATIONS:
- TYPE: Parent
  VALUE: REQ-VAL-042

[REQUIREMENT]
UID: TST-VAL-064
STATUS: Active
TITLE: Acceptance: mounted game APIs gate on requireGame
STATEMENT: >>>
Plan: Acceptance: mounted game APIs gate on requireGame
level: acceptance
verifies: USR-VAL-012, REQ-VAL-045, REQ-VAL-046, FNC-VAL-022, CMP-VAL-008, UNT-VAL-033
requires_tol: TOL-ROO-008, TOL-ROO-007
patterns: accept_require_game, api_gating
execution_status: blocked_on_tooling
evidence_status: none
cases:
  - With RO disabled, RO API calls surface game_required: expected=403 game_required observable to client
  - With AG disabled, AG API calls surface game_required: expected=403 game_required for adventurer-guild
  - After enable, corresponding mount succeeds past gate: expected=No game_required when enabled
<<<
COMMENT: >>>
domain: Games catalog
notes: Acceptance plans cite TOL-ROO-008 Playwright (and TOL-ROO-007 MSW where HTTP/session mocked). Catalog-only greenfield → blocked_on_tooling. USR allowed only because level=acceptance. evidence_status=none — Last Boss owns EVD. verifies = planned lineage only; published ≠ proven. No depends_on. No EVD/evidences. C-T1: never claim covered/done while blocked_on_tooling.
ssot_status: published
HONESTY: published plan only; not executed; no EVD.
<<<
RELATIONS:
- TYPE: Parent
  VALUE: REQ-VAL-045

[REQUIREMENT]
UID: TST-VAL-065
STATUS: Active
TITLE: Acceptance: SPA blocks disabled game paths and persists active game
STATEMENT: >>>
Plan: Acceptance: SPA blocks disabled game paths and persists active game
level: acceptance
verifies: USR-VAL-012, REQ-VAL-047, REQ-VAL-048, FNC-VAL-023, CMP-VAL-004, UNT-VAL-035
requires_tol: TOL-ROO-008, TOL-ROO-007
patterns: accept_spa_path_gate, valhalla_active_game
execution_status: blocked_on_tooling
evidence_status: none
cases:
  - Navigate to disabled game route → redirected off game path: expected=Landing matches post-login resolver; disabled game not shown
  - Selecting/using a game writes valhalla_active_game: expected=localStorage key holds active game id
  - Stale active game not in enabledGames is reconciled: expected=SPA recovers to an enabled game when available
<<<
COMMENT: >>>
domain: Games catalog
notes: Acceptance plans cite TOL-ROO-008 Playwright (and TOL-ROO-007 MSW where HTTP/session mocked). Catalog-only greenfield → blocked_on_tooling. USR allowed only because level=acceptance. evidence_status=none — Last Boss owns EVD. verifies = planned lineage only; published ≠ proven. No depends_on. No EVD/evidences. C-T1: never claim covered/done while blocked_on_tooling.
ssot_status: published
HONESTY: published plan only; not executed; no EVD.
<<<
RELATIONS:
- TYPE: Parent
  VALUE: REQ-VAL-047

[REQUIREMENT]
UID: TST-VAL-251
STATUS: Active
TITLE: GameScopedRowFilterStamp and PerGameRosterRow: Origin reads and writes never touch Ragnarok 3 records (Origin to Ragnarok 3 direction)
STATEMENT: >>>
Plan: GameScopedRowFilterStamp and PerGameRosterRow: Origin reads and writes never touch Ragnarok 3 records (Origin to Ragnarok 3 direction)
level: unit
verifies: REQ-VAL-205, REQ-VAL-206, FNC-ROO-207, FNC-ROO-208, UNT-VAL-218, UNT-VAL-219, CMP-VAL-027
requires_tol: TOL-ROO-006
patterns: isolation_origin_to_ro3, game_id_stamp, game_id_filter
execution_status: blocked_on_tooling
evidence_status: none
cases:
  - An Origin insert is stamped ragnarok-origin and leaves the Ragnarok 3 twin unchanged: expected=Origin row stamped game_id ragnarok-origin; the Ragnarok 3 row is unchanged
  - An Origin read filters by game: expected=the read returns nothing
  - An Origin update or remove leaves the Ragnarok 3 twin unchanged: expected=the Ragnarok 3 row is unchanged
  - Caches are keyed workspace::game: expected=cache key T::ragnarok-origin; it is never served to a ragnarok-3 read
  - One Discord member has one roster row per game: expected=two rows keyed (T, ragnarok-origin, u1) and (T, ragnarok-3, u1)
  - Changing a member's Origin roster entry leaves their Ragnarok 3 entry unchanged: expected=the Ragnarok 3 entry is unchanged
<<<
COMMENT: >>>
domain: Games catalog
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Direction: Origin to Ragnarok 3. Ragnarok 3 counterpart, text only: UNT-RO3-003. The reverse direction, as an Origin rule, is TST-VAL-252.
ssot_status: published
HONESTY: published plan only; not executed; no EVD.
<<<
RELATIONS:
- TYPE: Parent
  VALUE: REQ-VAL-205

[REQUIREMENT]
UID: TST-VAL-252
STATUS: Active
TITLE: GameScopedRowFilterStamp and PerGameRosterRow: Ragnarok 3 reads and writes never touch Origin records; legacy rows stay Origin (Ragnarok 3 to Origin direction)
STATEMENT: >>>
Plan: GameScopedRowFilterStamp and PerGameRosterRow: Ragnarok 3 reads and writes never touch Origin records; legacy rows stay Origin (Ragnarok 3 to Origin direction)
level: unit
verifies: REQ-VAL-205, REQ-VAL-206, FNC-ROO-207, FNC-ROO-208, UNT-VAL-218, UNT-VAL-219, CMP-VAL-027
requires_tol: TOL-ROO-006
patterns: isolation_ro3_to_origin, legacy_rows_origin
execution_status: blocked_on_tooling
evidence_status: none
cases:
  - A Ragnarok 3 write leaves the Origin twin unchanged: expected=the Origin row is unchanged
  - A Ragnarok 3 read does not return Origin records: expected=none of them is returned
  - Changing a member's Ragnarok 3 roster entry leaves their Origin entry unchanged: expected=the Origin entry is unchanged
  - Rows saved before game stamping count as Origin: expected=returned to an Origin read; not returned to a Ragnarok 3 read
  - Adventurer Guild documents count as Adventurer Guild: expected=returned under adventurer-guild only; not to an Origin or Ragnarok 3 read
<<<
COMMENT: >>>
domain: Games catalog
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Direction: Ragnarok 3 to Origin, as stated by the Origin units (UNT-VAL-218 invariant 1, UNT-VAL-219 algorithm 2, REQ-VAL-205 criterion 1, REQ-VAL-206 criterion 3). Ragnarok 3 counterpart, text only: UNT-RO3-003.
ssot_status: published
HONESTY: published plan only; not executed; no EVD.
<<<
RELATIONS:
- TYPE: Parent
  VALUE: REQ-VAL-205

[REQUIREMENT]
UID: TST-VAL-253
STATUS: Active
TITLE: Request context and store bind an explicit game; game data with no game set is refused with 'select a game' and never treated as Origin
STATEMENT: >>>
Plan: Request context and store bind an explicit game; game data with no game set is refused with 'select a game' and never treated as Origin
level: unit
verifies: REQ-VAL-158, REQ-VAL-205, FNC-VAL-159, FNC-ROO-207, UNT-VAL-169, UNT-VAL-218, CMP-VAL-008, CMP-VAL-027
requires_tol: TOL-ROO-006
patterns: explicit_game, select_a_game, no_origin_fallback
execution_status: blocked_on_tooling
evidence_status: none
cases:
  - runWithTenant keeps a game already set: expected=current game stays ragnarok-origin
  - runWithTenant supplies no default game: expected=current game is unset; it is not ragnarok-origin
  - A request reading game data with no game set is refused: expected=refused with a 'select a game' error; nothing read; Origin rows not returned
  - A request writing game data with no game set is refused: expected=refused with a 'select a game' error; nothing written in any game
  - A background job with no game set is refused: expected=refused with a 'select a game' error; nothing read or written
  - Workspace-level data needs no game: expected=not refused
  - Operational rows are stamped with the current game: expected=row stamped tenant_id T and game_id ragnarok-origin
  - clearTenantCaches clears every game key and keeps the channel cache tenant-only: expected=both game config entries cleared; the channel cache is keyed by T only
<<<
COMMENT: >>>
domain: Games catalog
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Code at f38e137 (cited only): backend/src/db/tenantContext.js:14-15 resolveGameId and backend/src/db/database.js:21-23 currentGameId default the game to ragnarok-origin and no 'select a game' error exists, so no-game cases are expected to fail at f38e137 (code gap (a), published on REQ-VAL-205/158, FNC-VAL-159/207, CMP-VAL-008). Tenant-resolution cases for UNT-VAL-169 stay in TST-VAL-206. Ragnarok 3 counterpart, text only: UNT-RO3-003.
ssot_status: published
HONESTY: published plan only; not executed; no EVD.
<<<
RELATIONS:
- TYPE: Parent
  VALUE: REQ-VAL-158

[REQUIREMENT]
UID: TST-VAL-258
STATUS: Active
TITLE: WorkspaceVsGameSettingsSplit: only Origin saves write workspace keys; a game save writes only its own game row
STATEMENT: >>>
Plan: WorkspaceVsGameSettingsSplit: only Origin saves write workspace keys; a game save writes only its own game row
level: unit
verifies: REQ-VAL-207, FNC-ROO-209, UNT-ROO-220, CMP-VAL-027
requires_tol: TOL-ROO-006
patterns: settings_split, workspace_keys_origin_only
execution_status: blocked_on_tooling
evidence_status: none
cases:
  - An Origin save splits workspace and game keys: expected=guildDisplayName and timezone written to tenant_settings; jobs written to game_settings(T, ragnarok-origin)
  - An Origin save leaves the Ragnarok 3 row unchanged: expected=game_settings(T, ragnarok-3) unchanged
  - Another game's save writes only its game row: expected=only game_settings(T, ragnarok-3) written; tenant_settings and the Origin row unchanged
  - Reads merge in the published order: expected=workspace defaults < game defaults < workspace < game; later wins; cached under T::game
  - A save or load with no game set is refused: expected=refused; nothing read or written
<<<
COMMENT: >>>
domain: Games catalog
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Code at f38e137 (cited only): backend/src/db/tenantContext.js:14-15 resolveGameId and backend/src/db/database.js:21-23 currentGameId default the game to ragnarok-origin and no 'select a game' error exists, so no-game cases are expected to fail at f38e137 (code gap (a), published on REQ-VAL-205/158, FNC-VAL-159/207, CMP-VAL-008). Ragnarok 3 counterpart, text only: UNT-RO3-004, UNT-RO3-008.
ssot_status: published
HONESTY: published plan only; not executed; no EVD.
<<<
RELATIONS:
- TYPE: Parent
  VALUE: REQ-VAL-207

[REQUIREMENT]
UID: TST-VAL-259
STATUS: Active
TITLE: OriginSettingsCarryOver copies leftover game keys into Origin only, never into Ragnarok 3
STATEMENT: >>>
Plan: OriginSettingsCarryOver copies leftover game keys into Origin only, never into Ragnarok 3
level: unit
verifies: REQ-VAL-208, FNC-ROO-210, UNT-ROO-221, CMP-VAL-027
requires_tol: TOL-ROO-006
patterns: origin_carry_over, never_copy_to_ro3
execution_status: blocked_on_tooling
evidence_status: none
cases:
  - An empty Origin row receives the old game keys: expected=non-workspace keys copied into the Origin row
  - A non-empty Origin row is not overwritten: expected=no copy
  - Workspace settings keep only workspace keys: expected=tenant_settings holds only guildDisplayName, timezone, adminRoles, guildLogoUrl
  - Leftover keys are copied into Origin on read: expected=key copied into the Origin row
  - Nothing is copied into Ragnarok 3: expected=the Ragnarok 3 row stays empty
  - Adventurer Guild documents are marked adventurer-guild: expected=marked adventurer-guild
<<<
COMMENT: >>>
domain: Games catalog
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done.
ssot_status: published
HONESTY: published plan only; not executed; no EVD.
<<<
RELATIONS:
- TYPE: Parent
  VALUE: REQ-VAL-208

[[/SECTION]]

[[SECTION]]
TITLE: Auction/Requests — TST-ROO-066 .. TST-ROO-092 (27 plans)

[REQUIREMENT]
UID: TST-ROO-066
STATUS: Active
TITLE: RequestLobbyBuilder returns a member-scoped lobby shared by HTTP init and Discord card
STATEMENT: >>>
Plan: RequestLobbyBuilder returns a member-scoped lobby shared by HTTP init and Discord card
level: unit
verifies: REQ-ROO-078, FNC-ROO-053, UNT-ROO-064, CMP-ROO-012
requires_tol: TOL-ROO-006
patterns: request_lobby, shared_builder, member_scope
execution_status: blocked_on_tooling
evidence_status: none
cases:
  - Authenticated member gets gate, items, and own pending counts: expected=lobby payload with gate/phase, active event items/limits, and that member's pending selections and net counts
  - Unauthenticated caller does not get a lobby: expected=unauthenticated error; no lobby payload
  - HTTP init and Discord Request Card share one builder result: expected=both callers receive the same lobby payload
  - Another member's selections do not appear: expected=lobby payload scoped to member A; member B's pending selections and net counts are not the returned selections
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-078

[REQUIREMENT]
UID: TST-ROO-067
STATUS: Active
TITLE: SubmitRequestSelections writes Pending deltas only while the registration gate is open
STATEMENT: >>>
Plan: SubmitRequestSelections writes Pending deltas only while the registration gate is open
level: unit
verifies: REQ-ROO-079, FNC-ROO-054, UNT-ROO-065, CMP-ROO-012
requires_tol: TOL-ROO-006
patterns: submit_selections, gate_423, pending_delta
execution_status: blocked_on_tooling
evidence_status: none
cases:
  - Open gate and in-cap selections write Pending Requested or Canceled deltas: expected=ledger delta rows (Requested or Canceled) with Pending selectionStatus; response is the updated lobby/selection view
  - Closed gate does not accept selections: expected=RequestDeckError 423; no successful Pending deltas
  - Empty selections do not write deltas: expected=400; no ledger deltas
  - Quantity above the event loot cap is rejected: expected=422; no successful Pending deltas
  - Missing member is refused: expected=submit refused; no Pending ledger deltas
  - HTTP submit and Discord Request Card use the same writer: expected=both paths write Pending Requested/Canceled deltas through submit_selections; no second ledger
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-079

[REQUIREMENT]
UID: TST-ROO-068
STATUS: Active
TITLE: CancelPendingRequest drops one item's pending qty and locks phase 3
STATEMENT: >>>
Plan: CancelPendingRequest drops one item's pending qty and locks phase 3
level: unit
verifies: REQ-ROO-080, FNC-ROO-055, UNT-ROO-066, CMP-ROO-012
requires_tol: TOL-ROO-006
patterns: cancel_pending, phase3_423
execution_status: blocked_on_tooling
evidence_status: none
cases:
  - Allowed phase cancels the full pending quantity for the item: expected=pending qty for that item dropped via Canceled delta; updated selection state returned
  - Phase 3 does not cancel: expected=RequestDeckError 423; pending qty not dropped
  - Missing item identity does not cancel: expected=400; no Canceled delta
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-080

[REQUIREMENT]
UID: TST-ROO-069
STATUS: Active
TITLE: MimicActiveSessionReader returns null, a fresh session, or a 24h catalog reset
STATEMENT: >>>
Plan: MimicActiveSessionReader returns null, a fresh session, or a 24h catalog reset
level: unit
verifies: REQ-ROO-083, FNC-ROO-058, UNT-ROO-067, CMP-ROO-012
requires_tol: TOL-ROO-006
patterns: active_session, stale_24h
execution_status: blocked_on_tooling
evidence_status: none
cases:
  - Missing session is null, not an error: expected=session null; no error
  - Session older than 24h is reset from catalog: expected=stored active_session replaced with the default structure seeded from configured items/active loots and a fresh lastUpdated; that reset session is returned
  - Session not older than 24h is returned and not reset: expected=returned session is the stored session (not a catalog reset), with defensive defaults for allocations/qtyPerPage as needed
  - Occupied snowflakes return occupant display names only: expected=session.members has only occupied uids with displayName; empty slots add nobody; stored active_session has no members map
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-083

[REQUIREMENT]
UID: TST-ROO-070
STATUS: Active
TITLE: MimicSessionOptimisticUpdate writes a session only when version is not lower
STATEMENT: >>>
Plan: MimicSessionOptimisticUpdate writes a session only when version is not lower
level: unit
verifies: REQ-ROO-084, FNC-ROO-059, UNT-ROO-068, CMP-ROO-012
requires_tol: TOL-ROO-006
patterns: optimistic_version, officer_session
execution_status: blocked_on_tooling
evidence_status: none
cases:
  - Officer write with version not lower stores the session: expected=stored session updated; lastUpdated stamped; updated session returned
  - Lower version does not overwrite the stored session: expected=version abort; stored session unchanged
  - Non-officer does not write: expected=403; stored session unchanged
  - Missing session payload does not write: expected=400; stored session unchanged
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-084

[REQUIREMENT]
UID: TST-ROO-071
STATUS: Active
TITLE: PerformCommitSession atomically writes history, flips statuses, and clears the session
STATEMENT: >>>
Plan: PerformCommitSession atomically writes history, flips statuses, and clears the session
level: unit
verifies: REQ-ROO-085, REQ-ROO-086, FNC-ROO-060, FNC-ROO-061, UNT-ROO-069, CMP-ROO-012
requires_tol: TOL-ROO-006
patterns: atomic_commit, status_flip, supersede_pending
execution_status: blocked_on_tooling
evidence_status: none
cases:
  - Officer commit writes history and clears the session in one bundle: expected=one atomic bundle writes loot_history rows and past_auctions awards, flips web_requests selectionStatus, and clears auction/active_session; commit result returned
  - Commit conflict leaves no partial writes: expected=no partial commit: loot_history, past_auctions, web_requests statuses, and active_session stay as they were
  - Selected winner with no pending becomes Selected and ForcedAdd: expected=selectionStatus Selected; quantity/liveStatus Done; ForcedAdd applied
  - Selected winner who already has a pending is not ForcedAdd: expected=selectionStatus Selected with quantity/liveStatus Done; ForcedAdd not applied
  - Absent allocation becomes Absent: expected=selectionStatus Absent
  - Not-selected allocation becomes NotSelected: expected=selectionStatus NotSelected
  - Earlier Pending rows are Superseded; the latest becomes terminal: expected=latest Pending becomes the terminal status; each earlier Pending becomes Superseded
  - Non-officer does not commit: expected=403; active_session not cleared; no history writes
  - Missing allocations do not commit: expected=400; active_session not cleared; no history writes
  - HTTP commit and auto-commit share this writer only: expected=both call perform_commit_session; no second commit writer
  - ForcedAdd member name is the roster display name when the client name is a snowflake: expected=ForcedAdd member and past_auction mem are the roster displayName, not the snowflake
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-085

[REQUIREMENT]
UID: TST-ROO-072
STATUS: Active
TITLE: AutoCommitSharedWriter calls performCommitSession or no-ops
STATEMENT: >>>
Plan: AutoCommitSharedWriter calls performCommitSession or no-ops
level: unit
verifies: REQ-ROO-087, FNC-ROO-062, UNT-ROO-070, CMP-ROO-012
requires_tol: TOL-ROO-006
patterns: auto_commit, shared_writer
execution_status: blocked_on_tooling
evidence_status: none
cases:
  - Due scheduler signal commits through the shared writer: expected=performCommitSession (UNT-ROO-069) is called; no alternate commit writer runs
  - Commit failure is logged and does not switch writers: expected=failure logged; no divergent write path is substituted
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-087

[REQUIREMENT]
UID: TST-ROO-073
STATUS: Active
TITLE: AuctionRosterSync ghosts missing Discord members and never ghosts dummies
STATEMENT: >>>
Plan: AuctionRosterSync ghosts missing Discord members and never ghosts dummies
level: unit
verifies: REQ-ROO-088, FNC-ROO-063, UNT-ROO-071, CMP-ROO-012
requires_tol: TOL-ROO-006
patterns: roster_sync, ghost_rules, circuit_503
execution_status: blocked_on_tooling
evidence_status: none
cases:
  - Officer sync upserts seen members and restores Ghost to Active: expected=auction/members upserted with displayName, syncedAt, and joinedAt; a Ghost seen again becomes Active
  - Members missing from Discord become Ghost: expected=that member is marked Ghost
  - dummy_* and isDummy do not become Ghost: expected=Ghost evaluation skipped; those placeholders are not marked Ghost
  - Non-officer does not sync: expected=403; auction/members unchanged
  - Open circuit does not ghost anyone: expected=temporary unavailable (503 circuit); no partial ghosting; auction/members unchanged
  - Discord fetch failure does not finish the sync: expected=Discord fetch failure; sync does not complete
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-088

[REQUIREMENT]
UID: TST-ROO-074
STATUS: Active
TITLE: ResetPriorityAdminReset appends an AdminReset row and keeps prior history
STATEMENT: >>>
Plan: ResetPriorityAdminReset appends an AdminReset row and keeps prior history
level: unit
verifies: REQ-ROO-089, FNC-ROO-064, UNT-ROO-072, CMP-ROO-012
requires_tol: TOL-ROO-006
patterns: admin_reset, append_only
execution_status: blocked_on_tooling
evidence_status: none
cases:
  - Officer reset inserts an AdminReset/Reset row: expected=new web_requests row with applicationStatus AdminReset, selectionStatus Reset, quantity 0, priority 0
  - Prior history rows stay as stored: expected=prior rows not rewritten; only the new AdminReset/Reset row is added
  - Non-officer does not insert a reset row: expected=403; no AdminReset row
  - Missing userId or itemId does not insert a reset row: expected=400; no AdminReset row
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-089

[REQUIREMENT]
UID: TST-ROO-075
STATUS: Active
TITLE: ClearRequestHistoryByDate deletes only web_requests inside an inclusive range
STATEMENT: >>>
Plan: ClearRequestHistoryByDate deletes only web_requests inside an inclusive range
level: unit
verifies: REQ-ROO-090, FNC-ROO-065, UNT-ROO-073, CMP-ROO-012
requires_tol: TOL-ROO-006
patterns: clear_history, inclusive_range
execution_status: blocked_on_tooling
evidence_status: none
cases:
  - Inclusive start and end dates are deleted: expected=those web_requests rows deleted; deletedCount equals the number removed
  - Dates outside the range are not deleted: expected=outside rows remain; they are not in deletedCount
  - Inverted or invalid range deletes nothing: expected=400; no web_requests deleted
  - Non-officer does not delete: expected=403; no web_requests deleted
  - Loot history and past auctions are not deleted by this unit: expected=deletedCount counts web_requests only; loot_history and past_auctions rows remain
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-090

[REQUIREMENT]
UID: TST-ROO-076
STATUS: Active
TITLE: RequestHistoryNewestFirst returns the ledger newest-first or an empty array
STATEMENT: >>>
Plan: RequestHistoryNewestFirst returns the ledger newest-first or an empty array
level: unit
verifies: REQ-ROO-091, FNC-ROO-066, UNT-ROO-074, CMP-ROO-012
requires_tol: TOL-ROO-006
patterns: request_history, newest_first
execution_status: blocked_on_tooling
evidence_status: none
cases:
  - Stored web_requests come back newest-first: expected=history[] ordered newest-first
  - Empty store is an empty array, not an error: expected=history[] is []; no error
<<<
COMMENT: >>>
domain: Auction/Requests
notes: Disagreement: REQ-ROO-091 now requires page/limit (default page 1, limit 20, clamp 1–10000), mine/status/q filters, export/preview, push-id date window, and sort modes. UNT-ROO-074 states newest-first history[] and empty store → []. Expected output follows the unit, not the amended requirement. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-091

[REQUIREMENT]
UID: TST-ROO-077
STATUS: Active
TITLE: LootHistoryNewestFirst returns loot rows newest-first or an empty array
STATEMENT: >>>
Plan: LootHistoryNewestFirst returns loot rows newest-first or an empty array
level: unit
verifies: REQ-ROO-092, FNC-ROO-067, UNT-ROO-075, CMP-ROO-012
requires_tol: TOL-ROO-006
patterns: loot_history, newest_first
execution_status: blocked_on_tooling
evidence_status: none
cases:
  - Loot history rows come back newest-first with date, event, item, and qty: expected=loot history[] ordered newest-first; each returned row carries date, event, item, and qty
  - Empty loot history is an empty array: expected=loot history[] is []; no error
<<<
COMMENT: >>>
domain: Auction/Requests
notes: Disagreement: REQ-ROO-092 now returns a date index {date, iso, count} and no history rows when date is omitted, or one night when date is set. UNT-ROO-075 states newest-first loot history[] with date/event/item/qty, empty → []. Expected output follows the unit, not the amended requirement. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-092

[REQUIREMENT]
UID: TST-ROO-078
STATUS: Active
TITLE: PastAuctionsWithMembersMap returns newest-first awards plus a members map
STATEMENT: >>>
Plan: PastAuctionsWithMembersMap returns newest-first awards plus a members map
level: unit
verifies: REQ-ROO-093, FNC-ROO-068, UNT-ROO-076, CMP-ROO-012
requires_tol: TOL-ROO-006
patterns: past_auctions, members_map
execution_status: blocked_on_tooling
evidence_status: none
cases:
  - Awards are newest-first and the members map is returned: expected=history[] of awards newest-first together with the members map
  - No awards still returns the members map: expected=empty awards; members map still returned; no error
<<<
COMMENT: >>>
domain: Auction/Requests
notes: Disagreement: REQ-ROO-093 now returns a date index and states it does not return a members map. UNT-ROO-076 states awards newest-first plus the auction/members map, including when awards are empty. Expected output follows the unit, not the amended requirement. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-093

[REQUIREMENT]
UID: TST-ROO-079
STATUS: Active
TITLE: MemberAuctionStatsSelfOrOfficer returns battle count and item awards for self or an officer
STATEMENT: >>>
Plan: MemberAuctionStatsSelfOrOfficer returns battle count and item awards for self or an officer
level: unit
verifies: REQ-ROO-094, FNC-ROO-069, UNT-ROO-077, CMP-ROO-012
requires_tol: TOL-ROO-006
patterns: member_stats, self_or_officer
execution_status: blocked_on_tooling
evidence_status: none
cases:
  - Omitted uid returns the caller's own stats: expected=battle count aggregated from loot_history and per-item award qty from past_auctions for the caller
  - Officer may read another member's stats: expected=battle count and per-item award qty for that uid
  - Non-officer cannot read another member: expected=403; no stats payload for that uid
  - A uid that is not a Discord snowflake is rejected: expected=400; no stats payload
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-094

[REQUIREMENT]
UID: TST-ROO-080
STATUS: Active
TITLE: SettingsHelpUrlsPublic returns member-safe help and clock fields
STATEMENT: >>>
Plan: SettingsHelpUrlsPublic returns member-safe help and clock fields
level: unit
verifies: REQ-ROO-095, FNC-ROO-070, UNT-ROO-078, CMP-ROO-012
requires_tol: TOL-ROO-006
patterns: help_urls, no_admin_leak
execution_status: blocked_on_tooling
evidence_status: none
cases:
  - Authenticated member receives help and clock fields without admin or channel maps: expected=help settings view of member-safe help/clock fields; adminRoles and discordChannels are not in the view
  - Unauthenticated caller gets no help view: expected=unauthenticated error; no help settings view
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-095

[REQUIREMENT]
UID: TST-ROO-081
STATUS: Active
TITLE: SettingsGetPublicVsOfficer returns the public view or the officer config
STATEMENT: >>>
Plan: SettingsGetPublicVsOfficer returns the public view or the officer config
level: unit
verifies: REQ-ROO-096, FNC-ROO-071, UNT-ROO-079, CMP-ROO-012
requires_tol: TOL-ROO-006
patterns: settings_get, public_only
execution_status: blocked_on_tooling
evidence_status: none
cases:
  - Non-officer gets the public view: expected=publicSettingsView plus help, needsSetup, and publicOnly true; discordChannels absent
  - Officer gets full config and discord channels: expected=full config, needsSetup, publicOnly false, and discordChannels
  - Unauthenticated caller gets no settings view: expected=unauthenticated error; neither public nor full settings view
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-096

[REQUIREMENT]
UID: TST-ROO-082
STATUS: Active
TITLE: SettingsSaveWorkspaceOrGame merges by scope and rejects overlapping raid cycles
STATEMENT: >>>
Plan: SettingsSaveWorkspaceOrGame merges by scope and rejects overlapping raid cycles
level: unit
verifies: REQ-ROO-097, FNC-ROO-072, UNT-ROO-080, CMP-ROO-012
requires_tol: TOL-ROO-006
patterns: settings_save, scope_merge, raid_overlap
execution_status: blocked_on_tooling
evidence_status: none
cases:
  - Workspace scope merges workspace keys only: expected=saved settings merge workspace keys only; non-workspace keys are not merged
  - Game scope merges non-workspace keys: expected=saved settings merge non-workspace keys
  - Omitted scope defaults to game: expected=save treated as scope=game (non-workspace keys merged)
  - Game scope may persist discordChannels: expected=discordChannels saved to tenant settings; saved settings returned
  - Overlapping raid cycles on game scope do not save: expected=400; settings not saved
  - Non-officer does not save: expected=403; settings not saved
  - Missing config does not save: expected=400; settings not saved
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-097

[REQUIREMENT]
UID: TST-ROO-083
STATUS: Active
TITLE: SettingsUnlockSession marks the current tenant session and returns the officer profile
STATEMENT: >>>
Plan: SettingsUnlockSession marks the current tenant session and returns the officer profile
level: unit
verifies: REQ-ROO-098, FNC-ROO-073, UNT-ROO-081, CMP-ROO-012
requires_tol: TOL-ROO-006
patterns: settings_unlock, session_tenant
execution_status: blocked_on_tooling
evidence_status: none
cases:
  - Officer unlock stores session flags for the current tenant: expected=session.settingsUnlocked set; settingsUnlockedTenantId is the current tenant; signed officer user profile returned
  - Unlock is not stored for a different tenant: expected=settingsUnlockedTenantId is T, not another tenant
  - Non-officer does not unlock: expected=403; settingsUnlocked not set
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-098

[REQUIREMENT]
UID: TST-ROO-084
STATUS: Active
TITLE: DiscordRequestCardInteractions open, submit, and drop through the shared deck
STATEMENT: >>>
Plan: DiscordRequestCardInteractions open, submit, and drop through the shared deck
level: unit
verifies: REQ-ROO-081, FNC-ROO-056, UNT-ROO-082, CMP-VAL-011
requires_tol: TOL-ROO-006
patterns: reqcard, shared_deck
execution_status: blocked_on_tooling
evidence_status: none
cases:
  - reqcard open builds a private panel from the shared lobby: expected=private request panel; lobby from RequestLobbyBuilder
  - reqcard submit writes through SubmitRequestSelections: expected=ledger write is SubmitRequestSelections into web_requests; no Discord-only ledger
  - reqcard drop writes through CancelPendingRequest: expected=drop calls CancelPendingRequest; no Discord-only ledger
  - Roster disconnect does not write a Discord-only ledger: expected=roster-disconnect reply; no Discord-only web_requests write
  - Gate lockdown follows deck/gate rules instead of a local write: expected=lockdown reply follows deck/gate rules; no second write path
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-081

[REQUIREMENT]
UID: TST-ROO-085
STATUS: Active
TITLE: InteractiveClaimPanel updates claims only while the live-claim gate is open
STATEMENT: >>>
Plan: InteractiveClaimPanel updates claims only while the live-claim gate is open
level: unit
verifies: REQ-ROO-082, FNC-ROO-057, UNT-ROO-083, CMP-VAL-011
requires_tol: TOL-ROO-006
patterns: claim_panel, gate_open, claim_limit
execution_status: blocked_on_tooling
evidence_status: none
cases:
  - Open gate and rostered member update the session claim: expected=auction/active_session slot claim updated with the snowflake; that member's displayName upserted from Discord
  - Closed live-claim gate does not change the session: expected=no active_session mutation
  - Member missing from the roster does not claim: expected=roster-disconnect reply; active_session unchanged
  - Collision or per-item limit does not write the conflicting claim: expected=claim collision/limit error; conflicting claim not stored
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-082

[REQUIREMENT]
UID: TST-ROO-086
STATUS: Active
TITLE: AuctionSpaRoutes maps four paths to the four auction tabs
STATEMENT: >>>
Plan: AuctionSpaRoutes maps four paths to the four auction tabs
level: unit
verifies: REQ-ROO-099, FNC-ROO-074, UNT-ROO-084, CMP-ROO-013
requires_tol: TOL-ROO-006
patterns: spa_routes, auction_tabs
execution_status: blocked_on_tooling
evidence_status: none
cases:
  - Root path renders the Request tab: expected=rendered auction tab is Request
  - Mimic Book path renders the Mimic Book tab: expected=rendered auction tab is Mimic Book
  - Request History path renders the Request History tab: expected=rendered auction tab is Request History
  - Past Auction path renders the Past Auction tab: expected=rendered auction tab is Past Auction
  - Game or billing gate redirect does not render an auction tab: expected=redirect from game/billing gates; auction tab not rendered
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-099

[REQUIREMENT]
UID: TST-ROO-087
STATUS: Active
TITLE: SubmitEvidenceRedirect sends /submit-evidence to / and serves no evidence page
STATEMENT: >>>
Plan: SubmitEvidenceRedirect sends /submit-evidence to / and serves no evidence page
level: unit
verifies: REQ-ROO-100, FNC-ROO-075, UNT-ROO-085, CMP-ROO-013
requires_tol: TOL-ROO-006
patterns: submit_evidence_redirect
execution_status: blocked_on_tooling
evidence_status: none
cases:
  - Legacy path redirects permanently to Request home: expected=permanent redirect to /
  - That path does not serve evidence submission: expected=no evidence submission UI and no evidence submission API on this path
<<<
COMMENT: >>>
domain: Auction/Requests
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-100

[REQUIREMENT]
UID: TST-ROO-088
STATUS: Active
TITLE: PityGuildCalendarDayScore returns night points and does not write stored priority
STATEMENT: >>>
Plan: PityGuildCalendarDayScore returns night points and does not write stored priority
level: unit
verifies: REQ-ROO-174, FNC-ROO-175, UNT-ROO-185, CMP-ROO-012
requires_tol: TOL-ROO-006
patterns: pity_score, calendar_day, stored_priority_untouched
execution_status: blocked_on_tooling
evidence_status: none
cases:
  - Parsed date or else eventDate, in YYYY-MM-DD or M/D/YYYY, sets the calendar day: expected=points 2
  - Unparseable date and eventDate do not count: expected=points 0
  - Days before the inclusive window do not count: expected=points 0 (window is today through today)
  - A row lookbackDays field does not replace the call argument: expected=points 0; the call window is used, not the row field
  - Days after today do not count: expected=points 0
  - A later-day Selected ends the streak even when its id sorts first: expected=points 0
  - Reset ends the streak: expected=points 0
  - Non-high-value Absent ends the streak and does not count as a night: expected=points 0
  - NotSelected after a non-high-value Absent counts, and the Absent night does not: expected=points 1
  - High-value Absent counts as one night and does not end the streak: expected=points 2
  - Two NotSelected rows on the same calendar day count once: expected=points 1
  - Pending, Superseded, and Canceled neither count nor end: expected=points 1
  - Returned points are computed; stored history.priority is not written: expected=return value is the number 1; each row's stored history.priority remains 9
<<<
COMMENT: >>>
domain: ROO delta 2026-10-03
notes: Disagreement: REQ-ROO-174 also requires lookback clamped to 1–365 (unset → 30), eventDate stamped on commit/reset, Request History rendering eventDate or '---', and lobby/Mimic/Discord/auto-commit display of the live score. UNT-ROO-185 states lookbackDays and isHighValue are call inputs, eventDate stamping is not this function, and the return is a number that does not write history.priority. Expected output follows the unit. userId, itemId, and itemName are named inputs, but the unit states no row-filter rule, so no case asserts one. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-174

[REQUIREMENT]
UID: TST-ROO-089
STATUS: Active
TITLE: AllocatePerItemRows returns selected and not-selected rows for items with loot qty
STATEMENT: >>>
Plan: AllocatePerItemRows returns selected and not-selected rows for items with loot qty
level: unit
verifies: REQ-ROO-179, FNC-ROO-180, UNT-ROO-190, CMP-ROO-012
requires_tol: TOL-ROO-006
patterns: allocate_rows, per_item
execution_status: blocked_on_tooling
evidence_status: none
cases:
  - Only items with lootSummary qty greater than 0 are listed: expected=selectedRows and notSelectedRows contain item A only; item B does not appear
  - Selected rows are unique non-empty uids ordered by rank then uid: expected=selectedRows has one row per non-empty uid; empty uid omitted; order is rank then uid
  - Not-selected rows are the ranking minus selected uids, in ranking order: expected=notSelectedRows are rankingsByItem minus the selected uids, in that ranking order
  - Each row has only the named fields: expected=every row has exactly key, itemId, itemName, uid, name, rank, rankLabel, and priority; no other field
  - rankLabel is the 1-based ranking index padded to two digits: expected=rankLabel is 01
  - A uid missing from the ranking gets an em dash rankLabel: expected=rankLabel is an em dash
  - Missing lobby priority is 0: expected=priority is 0
  - One row per item and member, not per loot slot: expected=one selected row for that item and member, not two
<<<
COMMENT: >>>
domain: ROO delta 2026-10-03
notes: Disagreement: REQ-ROO-179 also requires Review Allocation columns (no Requested column) and a GEN-room line '#{rank}  **{item}**  {member}  Prio {n}' plus Discord mention/chunk rules. UNT-ROO-190 returns {selectedRows, notSelectedRows} only and states announce HTTP is not this unit. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-179

[REQUIREMENT]
UID: TST-ROO-090
STATUS: Active
TITLE: ConfirmAllocateThenAnnounce writes the session before an empty announce POST
STATEMENT: >>>
Plan: ConfirmAllocateThenAnnounce writes the session before an empty announce POST
level: unit
verifies: REQ-ROO-180, FNC-ROO-181, UNT-ROO-191, CMP-ROO-012
requires_tol: TOL-ROO-006
patterns: confirm_allocate, announce_empty_body
execution_status: blocked_on_tooling
evidence_status: none
cases:
  - Confirm stores the named Mimic session fields first: expected=saved session has activeStep 2, preview loot summary, category allocations, initial winners, active matrix filter, and sidebarTab standby
  - Session write failure alerts and does not announce: expected=alert; POST /api/requests/announce-allocate is not called
  - Successful confirm posts announce with an empty body: expected=POST /api/requests/announce-allocate with an empty body; no client winner list is sent
  - Announce rebuilds rows from the saved session: expected=GEN announce rows rebuilt server-side from the saved session
  - Announce Live Auction posts the same route without the confirm-modal save: expected=POST /api/requests/announce-allocate without that confirm-modal write
  - No session identity is 401: expected=401
  - Non-officer is 403: expected=403
  - No active session is 400 with the named error: expected=400 and error 'No active Mimic Book session.'
  - Discord not configured is 400: expected=400
  - Discord offline, disconnected, rate-limited, or blocking is 503: expected=503
  - Discord target not found is 404: expected=404
  - In-flight confirm button reads Allocating and is disabled: expected=confirm button text is 'Allocating…' and the button is disabled
<<<
COMMENT: >>>
domain: ROO delta 2026-10-03
notes: Disagreement: REQ-ROO-180 quotes the alert 'Session saved locally, but the server write failed. Discord announce skipped.' and says the GEN message is built from the stored session plus the current request lobby. UNT-ROO-191 says write failure alerts and does not call announce, and that announce rebuilds rows from the saved session and does not take a client winner list. It does not state that alert sentence or a lobby merge. Expected output follows the unit. Level stays unit: the HTTP statuses are this unit's stated outcomes; no system layer was added, so API-ROO-115 is not in verifies. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-180

[REQUIREMENT]
UID: TST-ROO-091
STATUS: Active
TITLE: MimicBookLoadOnceEtag reloads on identity change and 304s a matching ETag
STATEMENT: >>>
Plan: MimicBookLoadOnceEtag reloads on identity change and 304s a matching ETag
level: unit
verifies: REQ-ROO-181, FNC-ROO-182, UNT-ROO-192, CMP-ROO-013
requires_tol: TOL-ROO-006
patterns: load_once, etag_304
execution_status: blocked_on_tooling
evidence_status: none
cases:
  - Leaving Mimic Book open does not repeat the session GET: expected=no repeating GET /api/requests/active-session
  - A new signed-in identity loads the session: expected=one session load for the new identity
  - No session uses ETag empty: expected=ETag is 'empty'
  - A stored session uses ETag s:version:lastUpdated: expected=ETag is s:{version}:{lastUpdated}
  - Matching If-None-Match returns 304 and no session body: expected=304; empty body; Cache-Control private, no-cache
  - A real GET still applies the 24-hour auto-reset: expected=24-hour auto-reset still applies; the page policy does not skip it
<<<
COMMENT: >>>
domain: ROO delta 2026-10-03
notes: UNT-ROO-192 states this is SPA page policy, not a new API, and that the ETag contract stays on API-034. Level stays unit, so API-ROO-034 is not in verifies. The 304 and ETag cases are rules the unit itself states. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-181

[REQUIREMENT]
UID: TST-ROO-092
STATUS: Active
TITLE: SettingsGetAllowlistedFields returns only requested allow-listed keys
STATEMENT: >>>
Plan: SettingsGetAllowlistedFields returns only requested allow-listed keys
level: unit
verifies: REQ-ROO-185, FNC-ROO-186, UNT-ROO-196, CMP-ROO-012
requires_tol: TOL-ROO-006
patterns: settings_field_pick, allow_list
execution_status: blocked_on_tooling
evidence_status: none
cases:
  - Requested allow-listed keys are the only keys returned: expected=response is the allow-listed subset jobs and timezone only
  - Unknown field names are dropped: expected=unknown name absent; jobs kept if allow-listed
  - Non-officer pick is the public view filtered before the pick: expected=public settings view is applied first; the returned pick is only allow-listed keys that remain on that public view, not the officer full config
  - Omitted fields still return the full officer view or the public view: expected=officer result is full officer config plus discord channels; non-officer result is the public view
<<<
COMMENT: >>>
domain: ROO delta 2026-10-03
notes: Disagreement: REQ-ROO-185 acceptance criteria also name wrapper fields success, needsSetup, and publicOnly on the fields response. UNT-ROO-196 states an allow-listed subset, unknown names dropped, public-view filter before the pick, and omitted fields returning the full officer config plus discord channels or the public view. It does not name those wrapper fields. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-185

[[/SECTION]]

[[SECTION]]
TITLE: Discord bot/Channels — TST-VAL-093 .. TST-VAL-110, TST-VAL-254 .. TST-VAL-256 (21 plans)

[REQUIREMENT]
UID: TST-VAL-093
STATUS: Active
TITLE: BotGatewayIntents enables exactly five gateway intents and not Presence
STATEMENT: >>>
Plan: BotGatewayIntents enables exactly five gateway intents and not Presence
level: unit
verifies: REQ-VAL-062, FNC-VAL-037, UNT-VAL-048, CMP-VAL-010
requires_tol: TOL-ROO-006
patterns: gateway_intents, presence_not_required
execution_status: blocked_on_tooling
evidence_status: none
cases:
  - Client construction enables exactly the five named intents: expected=client intents are exactly Guilds, GuildMessages, MessageContent, GuildMembers, and GuildVoiceStates
  - Presence Intent is not required: expected=client is constructed without Presence Intent; Presence is not required
  - Intents stay fixed after construction: expected=intents remain the five set at construction; they are not toggled per request
<<<
COMMENT: >>>
domain: Discord bot/Channels
notes: Disagreement: REQ-VAL-062 says bot intents include Guilds, GuildMessages, MessageContent, GuildMembers, and GuildVoiceStates. UNT-VAL-048 says exactly those five are enabled, Presence Intent is not required, and intents are fixed at construction. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-062

[REQUIREMENT]
UID: TST-VAL-094
STATUS: Active
TITLE: BotTokenInitGate refuses bot login when DISCORD_BOT_TOKEN is missing
STATEMENT: >>>
Plan: BotTokenInitGate refuses bot login when DISCORD_BOT_TOKEN is missing
level: unit
verifies: REQ-VAL-063, FNC-VAL-038, UNT-VAL-049, CMP-VAL-010
requires_tol: TOL-ROO-006
patterns: bot_token_gate, non_bot_http_still_boots
execution_status: blocked_on_tooling
evidence_status: none
cases:
  - Present token proceeds to bot login: expected=bot client init proceeds to login with the BotGatewayIntents client
  - Missing token is fatal for bot init and does not log in: expected=client init and login are refused; no successful client login
  - Bot init failure does not stop non-bot HTTP routes: expected=bot path stays fatal; HTTP API host may still serve non-bot routes
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-063

[REQUIREMENT]
UID: TST-VAL-095
STATUS: Active
TITLE: SlashCommandClearOnReady clears guild slash commands and replies ephemeral
STATEMENT: >>>
Plan: SlashCommandClearOnReady clears guild slash commands and replies ephemeral
level: unit
verifies: REQ-VAL-064, FNC-VAL-039, UNT-VAL-050, CMP-VAL-010
requires_tol: TOL-ROO-006
patterns: slash_clear_on_ready, ephemeral_redirect
execution_status: blocked_on_tooling
evidence_status: none
cases:
  - Ready clears guild slash commands for each onboarded tenant: expected=guild slash command registry emptied for each onboarded tenant
  - A per-tenant clear failure does not crash the bot: expected=that failure is logged; the process does not crash; clearing continues for the other tenants
  - A later slash invoke is an ephemeral redirect and does not re-register: expected=ephemeral reply that slash commands were removed and cards should be used (Request/attendance/party); commands are not re-registered
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-064

[REQUIREMENT]
UID: TST-VAL-096
STATUS: Active
TITLE: InteractionRouterByCustomId dispatches card prefixes and skips the general-room gate
STATEMENT: >>>
Plan: InteractionRouterByCustomId dispatches card prefixes and skips the general-room gate
level: unit
verifies: REQ-VAL-065, FNC-VAL-040, UNT-VAL-051, CMP-VAL-010
requires_tol: TOL-ROO-006
patterns: custom_id_route, general_room_bypass
execution_status: blocked_on_tooling
evidence_status: none
cases:
  - attcard prefix goes to the attendance card handler and skips the gate: expected=dispatched to the attendance card handler; general-room channel gate not applied
  - ocr prefix goes to the party OCR handler and skips the gate: expected=dispatched to the party OCR handler; general-room channel gate not applied
  - partycard prefix goes to the party viewer and skips the gate: expected=dispatched to the party viewer; general-room channel gate not applied
  - reqcard prefix goes to the request deck and skips the gate: expected=dispatched to the request deck; general-room channel gate not applied
  - Auction claim panel ids go to the interactive auction handler and skip the gate: expected=dispatched to the interactive auction handler; general-room channel gate not applied
  - onboard prefix goes to the onboarding card handler and skips the gate: expected=dispatched to the onboarding card handler; general-room channel gate not applied
  - An unknown prefix does not take a card route: expected=fall through to non-card handling; not dispatched as a card route
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-065

[REQUIREMENT]
UID: TST-VAL-097
STATUS: Active
TITLE: OnboardedTenantTicker runs a 60s clock and skips Discord announcers on the first tick or an open circuit
STATEMENT: >>>
Plan: OnboardedTenantTicker runs a 60s clock and skips Discord announcers on the first tick or an open circuit
level: unit
verifies: REQ-VAL-066, FNC-VAL-041, UNT-VAL-052, CMP-VAL-010
requires_tol: TOL-ROO-006
patterns: tenant_ticker, circuit_skip, jobs_not_on_clock
execution_status: blocked_on_tooling
evidence_status: none
cases:
  - After ready the ticker period is 60 seconds: expected=a per-onboarded-tenant interval whose period is 60 seconds
  - The first post-ready tick skips Discord announcers: expected=maybeAnnounceEvents and maybeAnnounceRaidEvents are not invoked on that first tick
  - A later tick with the circuit closed runs both Discord announcers: expected=maybeAnnounceEvents and maybeAnnounceRaidEvents are invoked; Discord-facing work goes through enqueueDiscordCall
  - An open circuit skips Discord announcers and still allows the non-Discord jobs: expected=Discord-facing announcers are not issued; maybeRefreshMonthlyLeaveCredits and maybeRunWarRoomAutomation may still run
  - closeExpiredDeadlines, refreshGvgReadinessBoard, maybeAutoCommitAuction and live-raid auto-end are not on this clock: expected=closeExpiredDeadlines, refreshGvgReadinessBoard, and maybeAutoCommitAuction are not invoked, and no live-raid auto-end job runs from this clock (removed in 9237b35, still absent at f38e137)
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Live-raid auto-end is not a job of this clock (UNT-VAL-052, FNC-VAL-041; removed in 9237b35, still absent at f38e137): the 60-second bot tick (discord-bot/client.js:257-286) has no auto-end. Automatic archiving of an Active live raid whose monitoring end time (monitoringEndsAt) has passed stays required behavior (REQ-ROO-144, FNC-ROO-137, UNT-ROO-147), whatever runs it; at f38e137 it runs only in runPulseOnce (backend/src/api/liveRaid.routes.js:204-216, archive call L211), which runs only inside the pulse ticker (startTicker L290-322) armed by armMonitoringSchedule (L327-394), and at boot in resumeLiveRaidMonitoringIfNeeded (L426-435, archive call L431; called from backend/src/index.js:27-32). Both archive through endLiveRaidSessionInternal (L571-684), the same path as officer End Raid. That archive rule is planned in TST-ROO-122, not in this plan; the code gap vs REQ-ROO-144 (Req Guardian ruling A) is recorded on FNC-ROO-137, FNC-VAL-041 and UNT-ROO-147.
ssot_status: published
HONESTY: published plan only; not executed; no EVD.
<<<
RELATIONS:
- TYPE: Parent
  VALUE: REQ-VAL-066

[REQUIREMENT]
UID: TST-VAL-098
STATUS: Active
TITLE: Discord429CircuitBreaker opens on 429, refuses outbound REST, and returns human status without secrets
STATEMENT: >>>
Plan: Discord429CircuitBreaker opens on 429, refuses outbound REST, and returns human status without secrets
level: unit
verifies: REQ-VAL-067, FNC-VAL-042, UNT-VAL-053, CMP-VAL-010
requires_tol: TOL-ROO-006
patterns: circuit_breaker, human_until, no_secrets
execution_status: blocked_on_tooling
evidence_status: none
cases:
  - A 429 with Retry-After stores an open circuit for that hold: expected=circuit_open is stored open with until and remaining for that Retry-After hold
  - A 429 or rate-limit/soft-ban with Retry-After omitted uses the default hold: expected=circuit opens for the default hold
  - Status returns human remaining and until and no secrets: expected=circuitOpen plus remaining and until as human strings; no secrets
  - Enqueue refuses outbound REST while the circuit is open: expected=outbound Discord REST is refused and not sent
  - Enqueue sends only after it sees the circuit closed: expected=circuit is checked closed before send; the call is sent and spaced
  - A non-local restart can hydrate stored circuit state from the platform store: expected=circuit_open, until, and remaining are hydrated from that store
<<<
COMMENT: >>>
domain: Discord bot/Channels
notes: Stored circuit_open/until/remaining and the human status strings are separate cases. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-067

[REQUIREMENT]
UID: TST-VAL-099
STATUS: Active
TITLE: DiscordHttpProxyOptional uses ProxyAgent only when a proxy URL is set
STATEMENT: >>>
Plan: DiscordHttpProxyOptional uses ProxyAgent only when a proxy URL is set
level: unit
verifies: REQ-VAL-068, FNC-VAL-043, UNT-VAL-054, CMP-VAL-010
requires_tol: TOL-ROO-006
patterns: optional_proxy, default_dispatcher
execution_status: blocked_on_tooling
evidence_status: none
cases:
  - A set proxy URL routes Discord HTTP through ProxyAgent: expected=Discord HTTP dispatcher is ProxyAgent; proxy takes precedence over the default dispatcher
  - A missing proxy does not fail boot and uses the IPv4-preferring dispatcher: expected=default IPv4-preferring dispatcher (PreferIpv4Discord); bot boot does not fail
  - An invalid proxy URL is an error: expected=invalid proxy URL error; not a successful proxy dispatcher
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-068

[REQUIREMENT]
UID: TST-VAL-100
STATUS: Active
TITLE: PreferIpv4Discord sets ipv4first and agent family 4 without disabling a configured proxy
STATEMENT: >>>
Plan: PreferIpv4Discord sets ipv4first and agent family 4 without disabling a configured proxy
level: unit
verifies: REQ-VAL-069, FNC-VAL-044, UNT-VAL-055, CMP-VAL-010
requires_tol: TOL-ROO-006
patterns: ipv4_preference, proxy_path_kept
execution_status: blocked_on_tooling
evidence_status: none
cases:
  - Non-proxy Discord REST prefers IPv4: expected=DNS default result order ipv4first and non-proxy Discord REST agent family 4
  - A configured proxy path is not disabled by the IPv4 preference: expected=proxy path stays in effect; IPv4 family-4 agent does not replace it
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-069

[REQUIREMENT]
UID: TST-VAL-101
STATUS: Active
TITLE: RateLimitDebugProbe returns bot and rate-limit status with no secrets and no login
STATEMENT: >>>
Plan: RateLimitDebugProbe returns bot and rate-limit status with no secrets and no login
level: system
verifies: REQ-VAL-076, FNC-VAL-051, API-VAL-029, UNT-VAL-056, CMP-VAL-010
requires_tol: TOL-ROO-006
patterns: debug_ratelimit, no_secrets
execution_status: blocked_on_tooling
evidence_status: none
cases:
  - GET with no login returns bot health merged with rate-limit status: expected=response merges botReady, botUser, and wsStatus with getDiscordRateLimitStatus fields
  - The response never includes the bot token or OAuth secrets: expected=bot token and OAuth secrets are absent from the response
<<<
COMMENT: >>>
domain: Discord bot/Channels
notes: Published unit states an HTTP contract, so level=system and verifies includes published API-VAL-029. API-VAL-029 also names success, remainingHuman, circuitUntilHuman, untilHuman, and oauthLoginExempt. UNT-VAL-056 states botReady, botUser, and wsStatus merged with getDiscordRateLimitStatus fields, and omits the bot token and OAuth secrets. It does not name those extra wrapper fields. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-076

[REQUIREMENT]
UID: TST-VAL-102
STATUS: Active
TITLE: CachedMemberNicknames returns a 2-minute cache or the roster and never bulk-fetches members
STATEMENT: >>>
Plan: CachedMemberNicknames returns a 2-minute cache or the roster and never bulk-fetches members
level: system
verifies: REQ-VAL-077, FNC-VAL-052, API-VAL-030, UNT-VAL-057, CMP-VAL-010
requires_tol: TOL-ROO-006
patterns: member_nickname_cache, roster_fallback, no_bulk_rest
execution_status: blocked_on_tooling
evidence_status: none
cases:
  - Missing tenant returns 409: expected=409 tenant_required
  - A non-empty gateway cache within 2 minutes returns those nickname rows and does not bulk REST-fetch: expected=member nickname/display rows from that cache; no bulk REST members fetch from the host/Render IP
  - An empty cache returns auction/members roster display names and does not bulk REST-fetch: expected=displayName rows from the auction/members roster; no bulk REST members fetch from the host/Render IP
<<<
COMMENT: >>>
domain: Discord bot/Channels
notes: Disagreement: REQ-VAL-077 says the fallback is a Postgres roster and that the route does not REST-fetch 1000 members from the Render IP. UNT-VAL-057 says an empty gateway cache falls back to auction/members roster displayName rows, never bulk REST-fetches guild members from the host/Render IP, and a missing tenant returns 409. Expected output follows the unit. Published unit states an HTTP contract, so level=system and verifies includes published API-VAL-030. API-VAL-030 also names member fields username, globalName, avatarURL, and joinedAt plus a success wrapper. UNT-VAL-057 states nickname/display rows or roster displayName rows. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-077

[REQUIREMENT]
UID: TST-VAL-103
STATUS: Active
TITLE: DeployRequestCard posts the Request Card to the mapped aucreq channel
STATEMENT: >>>
Plan: DeployRequestCard posts the Request Card to the mapped aucreq channel
level: system
verifies: REQ-VAL-070, FNC-VAL-045, API-VAL-024, UNT-VAL-058, CMP-VAL-011
requires_tol: TOL-ROO-006
patterns: deploy_request_card, aucreq_channel
execution_status: blocked_on_tooling
evidence_status: none
cases:
  - Officer deploy posts the Request Card (open request + live claim) to the mapped aucreq channel: expected=Request Card (open request + live claim) posted to the mapped aucreq channel from tenant discord_channels; success returned; process.env channel id is not used
  - Unmapped channel returns 400 and does not post: expected=400 and no card posted
  - Bot offline or an open circuit returns 503 and does not post: expected=503 and no card posted
  - A mapped channel that cannot be located returns 404 and does not post: expected=404 and no card posted
  - A caller who is not an authenticated officer returns 403 and does not post: expected=403 and no card posted
<<<
COMMENT: >>>
domain: Discord bot/Channels
notes: Published unit states an HTTP contract, so level=system and verifies includes published API-VAL-024. API-VAL-024 also names 401 unauthenticated, 409 tenant_required, and 500. UNT-VAL-058 states 400 unmapped, 503 bot offline or circuit open, 404 channel locate miss, and 403, and requires an authenticated officer and the current tenant. The channel comes from tenant discord_channels (aucreq), not process.env. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-070

[REQUIREMENT]
UID: TST-VAL-104
STATUS: Active
TITLE: DeployGvgReadinessCard posts the GVG readiness card only to mapped war-announce
STATEMENT: >>>
Plan: DeployGvgReadinessCard posts the GVG readiness card only to mapped war-announce
level: system
verifies: REQ-VAL-071, FNC-VAL-046, API-VAL-025, UNT-VAL-059, CMP-VAL-011
requires_tol: TOL-ROO-006
patterns: deploy_gvg_card, war_announce
execution_status: blocked_on_tooling
evidence_status: none
cases:
  - Officer deploy posts the GVG readiness/attendance card to the mapped war-announce channel: expected=GVG readiness/attendance card posted only to the mapped war-announce channel from tenant discord_channels; success returned; process.env channel id is not used; not posted to another mapping
  - Unmapped channel returns 400 and does not post: expected=400 and no card posted
  - Bot offline or an open circuit returns 503 and does not post: expected=503 and no card posted
  - A mapped channel that cannot be located returns 404 and does not post: expected=404 and no card posted
  - A caller who is not an authenticated officer returns 403 and does not post: expected=403 and no card posted
<<<
COMMENT: >>>
domain: Discord bot/Channels
notes: Published unit states an HTTP contract, so level=system and verifies includes published API-VAL-025. API-VAL-025 also names 401 unauthenticated, 409 tenant_required, and 500. UNT-VAL-059 states 400 unmapped, 503 bot offline or circuit open, 404 channel locate miss, and 403, and requires an authenticated officer and the current tenant. The channel comes from tenant discord_channels (warAnnounce), not process.env. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-071

[REQUIREMENT]
UID: TST-VAL-105
STATUS: Active
TITLE: DeployPartyViewerCard posts the party viewer card to mapped war-announce
STATEMENT: >>>
Plan: DeployPartyViewerCard posts the party viewer card to mapped war-announce
level: system
verifies: REQ-VAL-072, FNC-VAL-047, API-VAL-026, UNT-VAL-060, CMP-VAL-011
requires_tol: TOL-ROO-006
patterns: deploy_party_card, war_announce
execution_status: blocked_on_tooling
evidence_status: none
cases:
  - Officer deploy posts the party viewer card to the mapped war-announce channel: expected=party viewer card posted to the mapped war-announce channel from tenant discord_channels; success returned; process.env channel id is not used
  - Unmapped channel returns 400 and does not post: expected=400 and no card posted
  - Bot offline or an open circuit returns 503 and does not post: expected=503 and no card posted
  - A mapped channel that cannot be located returns 404 and does not post: expected=404 and no card posted
  - A caller who is not an authenticated officer returns 403 and does not post: expected=403 and no card posted
<<<
COMMENT: >>>
domain: Discord bot/Channels
notes: Published unit states an HTTP contract, so level=system and verifies includes published API-VAL-026. API-VAL-026 also names 401 unauthenticated, 409 tenant_required, and 500. UNT-VAL-060 states 400 unmapped, 503 bot offline or circuit open, 404 channel locate miss, and 403, and requires an authenticated officer and the current tenant. The channel comes from tenant discord_channels (warAnnounce), not process.env. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-072

[REQUIREMENT]
UID: TST-VAL-106
STATUS: Active
TITLE: DeployPartyOcrCard posts the party OCR card to mapped war-announce
STATEMENT: >>>
Plan: DeployPartyOcrCard posts the party OCR card to mapped war-announce
level: system
verifies: REQ-VAL-073, FNC-VAL-048, API-VAL-027, UNT-VAL-061, CMP-VAL-011
requires_tol: TOL-ROO-006
patterns: deploy_ocr_card, war_announce
execution_status: blocked_on_tooling
evidence_status: none
cases:
  - Officer deploy posts the party OCR card to the mapped war-announce channel: expected=party OCR card posted to the mapped war-announce channel from tenant discord_channels; success returned; process.env channel id is not used
  - Unmapped channel returns 400 and does not post: expected=400 and no card posted
  - Bot offline or an open circuit returns 503 and does not post: expected=503 and no card posted
  - A mapped channel that cannot be located returns 404 and does not post: expected=404 and no card posted
  - A caller who is not an authenticated officer returns 403 and does not post: expected=403 and no card posted
<<<
COMMENT: >>>
domain: Discord bot/Channels
notes: Published unit states an HTTP contract, so level=system and verifies includes published API-VAL-027. API-VAL-027 also names 401 unauthenticated, 409 tenant_required, and 500. UNT-VAL-061 states 400 unmapped, 503 bot offline or circuit open, 404 channel locate miss, and 403, and requires an authenticated officer and the current tenant. The channel comes from tenant discord_channels (warAnnounce), not process.env. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-073

[REQUIREMENT]
UID: TST-VAL-107
STATUS: Active
TITLE: AttendanceDeployAliases posts the same cards as the root deploy routes when mount gates allow it
STATEMENT: >>>
Plan: AttendanceDeployAliases posts the same cards as the root deploy routes when mount gates allow it
level: system
verifies: REQ-VAL-074, FNC-VAL-049, API-VAL-028, UNT-VAL-062, CMP-VAL-011
requires_tol: TOL-ROO-006
patterns: attendance_deploy_alias, mount_gates
execution_status: blocked_on_tooling
evidence_status: none
cases:
  - deploy-card posts the same card as deploy-attendance-card: expected=same card post as root GET /api/deploy-attendance-card
  - deploy-party-card posts the same card as root deploy-party-card: expected=same card post as root GET /api/deploy-party-card
  - deploy-ocr-card posts the same card as root deploy-ocr-card: expected=same card post as root GET /api/deploy-ocr-card
  - A failed attendance mount gate does not post: expected=403, 402, or 409 from the mount gates and no card post
  - Deploy failures stay the root deploy statuses: expected=400 when unmapped, 503 when bot offline or circuit open, 404 on locate miss; same posts as the root deploy routes, not a divergent alias result
<<<
COMMENT: >>>
domain: Discord bot/Channels
notes: Published unit states an HTTP contract, so level=system and verifies includes published API-VAL-028. API-VAL-028 also names 401 and a 403 game_required code plus a JSON success envelope {success, result}. UNT-VAL-062 states the three aliases (deploy-card same as deploy-attendance-card, deploy-party-card same as deploy-party-card, deploy-ocr-card same as deploy-ocr-card), mount-gate errors 403/402/409, deploy errors 400/503/404, and that aliases must not diverge from root deploy behavior. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-074

[REQUIREMENT]
UID: TST-VAL-108
STATUS: Active
TITLE: ChannelMapStorageResolver reads tenant discord_channels and never process.env
STATEMENT: >>>
Plan: ChannelMapStorageResolver reads tenant discord_channels and never process.env
level: unit
verifies: REQ-VAL-075, FNC-VAL-050, UNT-VAL-063, CMP-VAL-007
requires_tol: TOL-ROO-006
patterns: channel_map, no_env_fallback
execution_status: blocked_on_tooling
evidence_status: none
cases:
  - A stored discord_channels field resolves to that channel id: expected=resolved channel id is the stored JSON field value
  - An empty or missing mapped field stays empty: expected=resolved channel id is empty
  - process.env does not fill an empty mapped field: expected=process.env is not read; resolved channel id stays empty
<<<
COMMENT: >>>
domain: Discord bot/Channels
notes: Stored tenant_settings.discord_channels and the resolved channel id are separate cases. The env value does not count. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-075

[REQUIREMENT]
UID: TST-VAL-109
STATUS: Active
TITLE: Phase1GvgGetReadyLine posts the phase-1 get-ready sentence to GEN or sends nothing
STATEMENT: >>>
Plan: Phase1GvgGetReadyLine posts the phase-1 get-ready sentence to GEN or sends nothing
level: unit
verifies: REQ-VAL-190, FNC-VAL-191, UNT-ROO-201, CMP-VAL-010
requires_tol: TOL-ROO-006
patterns: phase1_get_ready, raid_announce_silence
execution_status: blocked_on_tooling
evidence_status: none
cases:
  - A due phase-1 minute posts the get-ready sentence to GEN: expected=GEN room receives exactly the get-ready sentence for warDate formatted Mon DD, YYYY; the message has no event title, no war start time, and no Jump in at clause when war-announce is unmapped
  - A mapped war-announce appends Jump in at the channel mention: expected=the GEN sentence ends with Jump in at <#id>. using the mapped warAnnounceChannelId
  - No scheduled phase minutes sends nothing: expected=raid-announce job sends nothing for that tick
  - Phase 2 or phase 3 does not use the get-ready sentence: expected=war-announce phase message is used; the GEN get-ready sentence is not posted for that phase
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-190

[REQUIREMENT]
UID: TST-VAL-110
STATUS: Active
TITLE: CachedOnboardedTenants reuses the list and settings caches and clears the list on lifecycle events
STATEMENT: >>>
Plan: CachedOnboardedTenants reuses the list and settings caches and clears the list on lifecycle events
level: unit
verifies: REQ-VAL-194, FNC-VAL-195, UNT-ROO-205, CMP-VAL-010
requires_tol: TOL-ROO-006
patterns: onboarded_list_cache, settings_cache, skip_no_access
execution_status: blocked_on_tooling
evidence_status: none
cases:
  - A populated list cache is reused: expected=iteration reuses that list cache and does not reload the onboarded-tenant list
  - Cached configuration and channels skip loadTenantSettings: expected=loadTenantSettings is not called for that tenant
  - Lifecycle events clear the onboarded list cache: expected=onboarded-tenant list cache is cleared
  - A tenant without access is skipped: expected=that tenant is skipped
<<<
COMMENT: >>>
domain: Discord bot/Channels
notes: Disagreement: REQ-VAL-194 says a 60-second tick does not call listOnboardedTenants while the in-process list cache is populated, and that creating a tenant, marking one onboarded, or activating/reverting billing clears the list so the next tick reloads. UNT-ROO-205 says reuse the in-process onboarded-tenant list cache, do not call loadTenantSettings when both configuration and channels are already cached, clear the list cache on tenant create, mark onboarded, billing activation, and automatic founding-seat revert, and still skip tenants without access. It does not name listOnboardedTenants. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-194

[REQUIREMENT]
UID: TST-VAL-254
STATUS: Active
TITLE: InteractionRouterByCustomId sets Origin explicitly on Origin card presses, never routes a Ragnarok 3 card press to Origin, and refuses an unknown game
STATEMENT: >>>
Plan: InteractionRouterByCustomId sets Origin explicitly on Origin card presses, never routes a Ragnarok 3 card press to Origin, and refuses an unknown game
level: unit
verifies: REQ-VAL-205, FNC-VAL-040, UNT-VAL-051, CMP-VAL-010
requires_tol: TOL-ROO-006
patterns: explicit_origin_press, ro3_press_not_origin, select_a_game
execution_status: blocked_on_tooling
evidence_status: none
cases:
  - An Origin card press runs with Origin set explicitly: expected=the handler runs with game ragnarok-origin set explicitly, not by default
  - An Origin press reads and writes Origin data only: expected=Origin records change; no Ragnarok 3 record or card changes
  - A press on a Ragnarok 3 card is not routed to an Origin handler: expected=no Origin handler is invoked; no Origin record changes
  - A press whose game cannot be determined changes nothing: expected=refused with a 'select a game' error; nothing changes; not handled as Origin
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Code at f38e137 (cited only): discord-bot/client.js wraps presses in runWithTenant (game defaults to Origin) and routes every ocr:* press to the Origin handler, so cases 1, 3 and 4 are expected to fail at f38e137 (code gap (b) on FNC-VAL-040, UNT-VAL-051). Prefix routing stays in TST-VAL-096. Ragnarok 3 counterpart, text only: UNT-RO3-033.
ssot_status: published
HONESTY: published plan only; not executed; no EVD.
<<<
RELATIONS:
- TYPE: Parent
  VALUE: REQ-VAL-205

[REQUIREMENT]
UID: TST-VAL-255
STATUS: Active
TITLE: Origin root card deploys (auction, attendance, party, ocr) are accepted only with Origin enabled and touch only Origin data and cards
STATEMENT: >>>
Plan: Origin root card deploys (auction, attendance, party, ocr) are accepted only with Origin enabled and touch only Origin data and cards
level: system
verifies: REQ-VAL-211, FNC-VAL-045, FNC-VAL-046, FNC-VAL-047, FNC-VAL-048, API-VAL-024, API-VAL-025, API-VAL-026, API-VAL-027, UNT-VAL-058, UNT-VAL-059, UNT-VAL-060, UNT-VAL-061, CMP-VAL-011
requires_tol: TOL-ROO-006
patterns: deploy_game_gate, origin_card_pointer, never_touch_ro3_card
execution_status: blocked_on_tooling
evidence_status: none
cases:
  - deploy-auction-card without Origin enabled is refused: expected=403 {code: 'game_required', gameId: 'ragnarok-origin'}; nothing posted
  - deploy-attendance-card without Origin enabled is refused: expected=403 {code: 'game_required', gameId: 'ragnarok-origin'}; nothing posted
  - deploy-party-card without Origin enabled is refused: expected=403 {code: 'game_required', gameId: 'ragnarok-origin'}; nothing posted
  - deploy-ocr-card without Origin enabled is refused: expected=403 {code: 'game_required', gameId: 'ragnarok-origin'}; nothing posted
  - Ragnarok 3 enabled alone does not count: expected=403 game_required naming ragnarok-origin; nothing posted
  - An accepted deploy runs in the Origin context and keeps its pointer as Origin data: expected=the deploy runs with game ragnarok-origin set; the card pointer is read and written as Origin data
  - The Ragnarok 3 card in the same channel is not touched: expected=the Ragnarok 3 message is not edited, replaced or removed; the Ragnarok 3 pointer record is unchanged
  - No Ragnarok 3 record changes: expected=every Ragnarok 3 record is unchanged
  - An inactive seat does not refuse these root routes: expected=not refused with 402; these root routes have no seat check
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Code at f38e137 (cited only): backend/src/createApp.js:135, 165, 181, 197 and 213 guard the root deploy routes with requireOfficerTenant only (no game gate; they run with no game set and fall back to Origin), so the game-gate cases are expected to fail at f38e137 (code gap on FNC-VAL-045..048, FNC-VAL-202, API-VAL-024..027, API-VAL-118). Officer, mapping and Discord status cases stay in TST-VAL-103..106. Ragnarok 3 counterpart, text only: UNT-RO3-031 / UNT-RO3-032.
ssot_status: published
HONESTY: published plan only; not executed; no EVD.
<<<
RELATIONS:
- TYPE: Parent
  VALUE: REQ-VAL-211

[REQUIREMENT]
UID: TST-VAL-256
STATUS: Active
TITLE: Attendance deploy aliases refuse without Origin enabled and touch only Origin data and cards
STATEMENT: >>>
Plan: Attendance deploy aliases refuse without Origin enabled and touch only Origin data and cards
level: system
verifies: REQ-VAL-211, FNC-VAL-049, API-VAL-028, UNT-VAL-062, CMP-VAL-011
requires_tol: TOL-ROO-006
patterns: deploy_game_gate, origin_card_pointer
execution_status: blocked_on_tooling
evidence_status: none
cases:
  - Each alias without Origin enabled is refused: expected=403 {code: 'game_required', gameId: 'ragnarok-origin'} each; nothing posted
  - Ragnarok 3 enabled alone does not count: expected=403 game_required naming ragnarok-origin; nothing posted
  - An accepted alias deploy runs in the Origin context with an Origin pointer: expected=game ragnarok-origin set; pointer read and written as Origin data
  - No Ragnarok 3 card or record changes: expected=Ragnarok 3 message and every Ragnarok 3 record unchanged
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Met at f38e137 for the gate (aliases sit behind requireGame(ragnarok-origin), backend/src/createApp.js:102). Same-send and mount-gate cases stay in TST-VAL-107.
ssot_status: published
HONESTY: published plan only; not executed; no EVD.
<<<
RELATIONS:
- TYPE: Parent
  VALUE: REQ-VAL-211

[[/SECTION]]

[[SECTION]]
TITLE: Live Raid/Voice — TST-ROO-111 .. TST-ROO-130 (20 plans)

[REQUIREMENT]
UID: TST-ROO-111
STATUS: Active
TITLE: CreateLiveRaidFromPublished starts one Active session and rejects duplicates, unresolved rooms, and cross-tab collisions
STATEMENT: >>>
Plan: CreateLiveRaidFromPublished starts one Active session and rejects duplicates, unresolved rooms, and cross-tab collisions
level: system
verifies: REQ-ROO-133, FNC-ROO-126, API-ROO-089, UNT-ROO-136, CMP-ROO-022
requires_tol: TOL-ROO-006
patterns: one_active_session, cross_tab_reject, tallies_zeroed
execution_status: blocked_on_tooling
evidence_status: none
cases:
  - Officer create stores one Active session with zeroed tallies: expected=attendance/live_session is stored with status Active, the grids, tallies zeroed, and launchedBy the officer display name
  - An existing live_session does not count as another start: expected=400 duplicate session; a second Active live_session is not started
  - War rooms that resolve to no channel are rejected: expected=create is rejected; no Active live_session is stored
  - A missing published composition is rejected: expected=404 or 400; no Active live_session is stored
  - Empty selected grids are rejected: expected=404 or 400; no Active live_session is stored
  - Fewer than one selected war room is rejected: expected=create is rejected; no Active live_session is stored
  - Cross-tab member collisions are rejected with the duplicates list: expected=400 with that duplicates list; no Active live_session is stored
  - A non-officer is rejected: expected=403; no Active live_session is stored
  - Optional monitoring fields are handed to the arm schedule: expected=ArmLiveRaidMonitoringSchedule is invoked with those monitoring fields
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-133

[REQUIREMENT]
UID: TST-ROO-112
STATUS: Active
TITLE: GetActiveLiveRaidSession returns null or snowflake-normalized war rooms and may store legacy id normalization
STATEMENT: >>>
Plan: GetActiveLiveRaidSession returns null or snowflake-normalized war rooms and may store legacy id normalization
level: system
verifies: REQ-ROO-134, FNC-ROO-127, API-ROO-090, UNT-ROO-137, CMP-ROO-022
requires_tol: TOL-ROO-006
patterns: null_session_success, snowflake_normalize, legacy_writeback
execution_status: blocked_on_tooling
evidence_status: none
cases:
  - No live_session returns null and that null counts as success: expected=returned session is null; the response is success
  - Returned war rooms are normalized to Discord snowflakes: expected=the returned session's war rooms are Discord channel snowflakes resolved through the warRooms catalog
  - Legacy relational ids are stored back separately from the returned view: expected=normalized selectedWarRooms and selectedWarRoomIds are written back on the live_session
  - An unauthenticated caller is rejected: expected=unauthenticated error; no successful session body
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-134

[REQUIREMENT]
UID: TST-ROO-113
STATUS: Active
TITLE: UpdateLiveRaidSession stores the officer patch and rejects cross-tab duplicate grids
STATEMENT: >>>
Plan: UpdateLiveRaidSession stores the officer patch and rejects cross-tab duplicate grids
level: system
verifies: REQ-ROO-135, FNC-ROO-128, API-ROO-091, UNT-ROO-138, CMP-ROO-022
requires_tol: TOL-ROO-006
patterns: session_patch, cross_tab_on_grids
execution_status: blocked_on_tooling
evidence_status: none
cases:
  - An officer patch is stored on the live session: expected=attendance/live_session is updated with the provided session patch
  - A patch without grids does not take the cross-tab reject: expected=the session patch is stored; cross-tab duplicates are not a reject for that patch
  - Grids with a multi-tab member do not count as an accepted patch: expected=400 with the duplicates; that grid patch is not stored
  - No live session is 404: expected=404
  - A non-officer is rejected: expected=403
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-135

[REQUIREMENT]
UID: TST-ROO-114
STATUS: Active
TITLE: AtomicLiveRaidCellUpdate clears other slots before placing and clears only the target when userId is empty
STATEMENT: >>>
Plan: AtomicLiveRaidCellUpdate clears other slots before placing and clears only the target when userId is empty
level: system
verifies: REQ-ROO-136, FNC-ROO-129, API-ROO-092, UNT-ROO-139, CMP-ROO-022
requires_tol: TOL-ROO-006
patterns: clear_then_set, empty_user_clears_target
execution_status: blocked_on_tooling
evidence_status: none
cases:
  - Placing a uid nulls that uid on other slots first, then sets the target: expected=matching userId is nulled on every other slot first, then the target coord is set, under attendance/live_session/grids
  - An empty userId clears the target only: expected=the target coord is cleared only; other slots are not cleared
  - No active live_session is 404: expected=404
  - A missing grid tab is 404: expected=404
  - A non-officer is rejected: expected=403
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-136

[REQUIREMENT]
UID: TST-ROO-115
STATUS: Active
TITLE: ResolveVoicePresence returns present UIDs or a 503 with empty UIDs when the Discord circuit is open
STATEMENT: >>>
Plan: ResolveVoicePresence returns present UIDs or a 503 with empty UIDs when the Discord circuit is open
level: system
verifies: REQ-ROO-137, FNC-ROO-130, API-ROO-093, UNT-ROO-140, CMP-ROO-022
requires_tol: TOL-ROO-006
patterns: present_uids, circuit_open_503, read_only_presence
execution_status: blocked_on_tooling
evidence_status: none
cases:
  - A closed circuit returns present UIDs for resolved war-room channels: expected=presentUids are the Discord member UIDs present in those voice channels
  - An open circuit does not count as a successful presence read: expected=503 with a human until hint and empty presentUids; stale presentUids are not returned as success
  - Presence is read-only: expected=presentUids are returned and no durable presence record is written
  - An unauthenticated caller is rejected: expected=unauthenticated error
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-137

[REQUIREMENT]
UID: TST-ROO-116
STATUS: Active
TITLE: ArmLiveRaidMonitoringSchedule stores the window, clears prior tickers, and sets scheduled, running, or ended
STATEMENT: >>>
Plan: ArmLiveRaidMonitoringSchedule stores the window, clears prior tickers, and sets scheduled, running, or ended
level: system
verifies: REQ-ROO-138, FNC-ROO-131, API-ROO-094, UNT-ROO-141, CMP-ROO-022
requires_tol: TOL-ROO-006
patterns: poll_interval_at_least_15, ticker_status, end_already_past
execution_status: blocked_on_tooling
evidence_status: none
cases:
  - A valid window stores the three monitoring fields: expected=those three monitoring fields are persisted on the live_session and the write-back matches the stored fields
  - Arming clears prior tickers and starts or schedules the pulse: expected=prior tickers are cleared; monitoringTickerStatus is scheduled or running; VoicePulseTally is started or scheduled
  - An end that is already past does not start a ticker: expected=monitoringTickerStatus is ended; a ticker is not started
  - A missing field, an interval under 15, or endsAt not after startsAt is an invalid window: expected=400 invalid window; the schedule is not armed
  - No Active session is 404: expected=404
  - A non-officer is rejected: expected=403
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-138

[REQUIREMENT]
UID: TST-ROO-117
STATUS: Active
TITLE: VoicePulseTally increments stored tallies, ignores a half-interval re-entry, and writes nothing when the circuit is open
STATEMENT: >>>
Plan: VoicePulseTally increments stored tallies, ignores a half-interval re-entry, and writes nothing when the circuit is open
level: unit
verifies: REQ-ROO-139, FNC-ROO-132, UNT-ROO-142, CMP-ROO-022
requires_tol: TOL-ROO-006
patterns: pulse_tally, half_interval_dedupe, circuit_open_skip
execution_status: blocked_on_tooling
evidence_status: none
cases:
  - The first pulse is immediate and later pulses follow the poll interval: expected=the first pulse runs immediately, then a pulse runs every pollIntervalMs
  - An in-window pulse stores totalPulses, per-uid tallies, and lastVoicePoll: expected=totalPulses is incremented, per-uid userTallies are incremented, and lastVoicePoll is written
  - An open Discord circuit does not count as a tally: expected=no tally write
  - A re-entry inside the dedupe window does not count: expected=the re-entry is ignored; totalPulses and userTallies are not incremented
  - A reached end or a session that is not Active stops the pulse: expected=the pulse stops and does not write a tally
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-139

[REQUIREMENT]
UID: TST-ROO-118
STATUS: Active
TITLE: EndLiveRaidAndArchive stores the archive and a commitments snapshot, computes expectedPulses, and clears the session
STATEMENT: >>>
Plan: EndLiveRaidAndArchive stores the archive and a commitments snapshot, computes expectedPulses, and clears the session
level: system
verifies: REQ-ROO-140, FNC-ROO-133, API-ROO-095, UNT-ROO-143, CMP-ROO-022
requires_tol: TOL-ROO-006
patterns: session_archive, expected_pulses, tickers_cleared
execution_status: blocked_on_tooling
evidence_status: none
cases:
  - Officer or internal end stores the archive and clears the live session: expected=a session_archive leaf is stored with tallies, the endedEarly flag, and attendance/live_session is set null
  - The commitments snapshot is stored separately from the computed pulse count: expected=the archive leaf stores that RSVP commitments snapshot for raid-roster members
  - expectedPulses is computed from monitored duration and the poll interval: expected=expectedPulses equals actual monitored duration divided by pollIntervalMinutes
  - End always clears both tickers: expected=liveRaidIntervalTicker and monitoringSchedulerTicker are stopped
  - An early end after monitoring started captures the final pulse first: expected=CaptureFinalMonitoringPulse runs before the archive write
  - A non-officer HTTP end is rejected: expected=403
  - No session is 404: expected=404
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-140

[REQUIREMENT]
UID: TST-ROO-119
STATUS: Active
TITLE: CaptureFinalMonitoringPulse applies one closing pulse or skips when monitoring never started or dedupe hits
STATEMENT: >>>
Plan: CaptureFinalMonitoringPulse applies one closing pulse or skips when monitoring never started or dedupe hits
level: unit
verifies: REQ-ROO-141, FNC-ROO-134, UNT-ROO-144, CMP-ROO-022
requires_tol: TOL-ROO-006
patterns: final_pulse, skip_before_start, dedupe_not_bypassed
execution_status: blocked_on_tooling
evidence_status: none
cases:
  - An early end outside the dedupe window applies one closing pulse: expected=applyPulseTally runs after war-room normalize, so the closing pulse can update tallies and lastVoicePoll
  - Monitoring that never started does not count as a final pulse: expected=the final pulse is skipped; tallies are not updated by this helper
  - A lastVoicePoll inside the half-interval dedupe does not count: expected=the final pulse is skipped; VoicePulseTally dedupe is not bypassed
<<<
COMMENT: >>>
domain: Live Raid/Voice
notes: Disagreement: REQ-ROO-141 says an early end captures a final pulse when monitoring had started and the end is before the scheduled end. UNT-ROO-144 says skip when monitoring never started (now < monitoringStartsAt) or there is no monStart, and still respect half-interval dedupe against lastVoicePoll so that window does not count as another pulse. It must not bypass VoicePulseTally dedupe. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-141

[REQUIREMENT]
UID: TST-ROO-120
STATUS: Active
TITLE: CancelLiveRaidWithoutArchive clears the session and the pulse ticker and does not write an archive
STATEMENT: >>>
Plan: CancelLiveRaidWithoutArchive clears the session and the pulse ticker and does not write an archive
level: system
verifies: REQ-ROO-142, FNC-ROO-135, API-ROO-096, UNT-ROO-145, CMP-ROO-022
requires_tol: TOL-ROO-006
patterns: cancel_no_archive, ticker_cleared
execution_status: blocked_on_tooling
evidence_status: none
cases:
  - Officer cancel stores a null session and does not archive: expected=attendance/live_session is set null; no session_archive leaf is written
  - A set pulse ticker is cleared: expected=liveRaidIntervalTicker is cleared
  - A non-officer cancel does not count: expected=403; the live_session is not cleared and no archive is written
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-142

[REQUIREMENT]
UID: TST-ROO-121
STATUS: Active
TITLE: ResumeMonitoringOnBoot re-arms inside the window, archives when the window has passed, and no-ops otherwise
STATEMENT: >>>
Plan: ResumeMonitoringOnBoot re-arms inside the window, archives when the window has passed, and no-ops otherwise
level: unit
verifies: REQ-ROO-143, FNC-ROO-136, UNT-ROO-146, CMP-ROO-022
requires_tol: TOL-ROO-006
patterns: boot_rearm, past_window_archive, boot_noop
execution_status: blocked_on_tooling
evidence_status: none
cases:
  - An Active session still in the window is re-armed from stored fields: expected=ArmLiveRaidMonitoringSchedule is called with the stored monitoringStartsAt, monitoringEndsAt, and poll interval
  - A window already past does not count as a resumed ticker: expected=EndLiveRaidAndArchive internal runs; the in-window ticker is not resumed
  - No Active session or missing monitoring fields do not count: expected=no-op; no re-arm and no archive
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-143

[REQUIREMENT]
UID: TST-ROO-122
STATUS: Active
TITLE: AutoEndLiveRaidOnWindowEnd archives through the shared end path when monitoringEndsAt is reached and skips otherwise
STATEMENT: >>>
Plan: AutoEndLiveRaidOnWindowEnd archives through the shared end path when monitoringEndsAt is reached and skips otherwise
level: unit
verifies: REQ-ROO-144, FNC-ROO-137, UNT-ROO-147, CMP-ROO-022
requires_tol: TOL-ROO-006
patterns: auto_end_window, active_guard_skip
execution_status: blocked_on_tooling
evidence_status: none
cases:
  - An Active session whose end has been reached is archived: expected=the session is archived through endLiveRaidSessionInternal (EndLiveRaidAndArchive internal), the same archive path as officer End Raid, with no officer action
  - No session, a non-Active status, or an end still in the future does not count: expected=skip; no archive
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Archiving an Active live raid once monitoringEndsAt has passed is behavior, not a required clock (UNT-ROO-147 responsibility and algorithm 1, FNC-ROO-137 behavior, REQ-ROO-144): it must happen whether or not an in-memory ticker is running and whether or not the process restarted. The 60-second bot tick (discord-bot/client.js:257-286) has no auto-end (removed in 9237b35, still absent at f38e137; UNT-ROO-147 notes). At f38e137 the end-time check runs only in runPulseOnce (backend/src/api/liveRaid.routes.js:204-216, Active re-check L210, archive call L211), which runs only inside the pulse ticker (startTicker L290-322) armed by armMonitoringSchedule (L327-394), and at boot in resumeLiveRaidMonitoringIfNeeded (L426-435, archive call L431; called from backend/src/index.js:27-32). Both archive through endLiveRaidSessionInternal (L571-684; EndLiveRaidAndArchive, UNT-ROO-143), the same path as officer End Raid. Skips in code: runPulseOnce returns without archiving when the session is missing or not Active (L199-202); the boot path returns when the session is missing or not Active (L419) or has no monitoring schedule (L422-425). Case 1 can be driven through either runner; while the pulse ticker is not running and the process does not restart, nothing reaches case 1 at f38e137. That is the code gap vs REQ-ROO-144 recorded on UNT-ROO-147 and FNC-ROO-137 (Req Guardian ruling A), not a plan defect. While the Discord rate-limit circuit is open, runPulseOnce returns before its end check (L194-197); that only delays archiving until the first pulse after the circuit closes.
ssot_status: published
HONESTY: published plan only; not executed; no EVD.
<<<
RELATIONS:
- TYPE: Parent
  VALUE: REQ-ROO-144

[REQUIREMENT]
UID: TST-ROO-123
STATUS: Active
TITLE: ListLiveRaidArchives returns the session_archive map or an empty object
STATEMENT: >>>
Plan: ListLiveRaidArchives returns the session_archive map or an empty object
level: system
verifies: REQ-ROO-145, FNC-ROO-138, API-ROO-097, UNT-ROO-148, CMP-ROO-022
requires_tol: TOL-ROO-006
patterns: archive_map, empty_object
execution_status: blocked_on_tooling
evidence_status: none
cases:
  - A populated archive is returned as the sessions object: expected=the sessions object from attendance/session_archive is returned
  - An empty archive does not count as a list of sessions: expected={}
  - The list does not write the archive: expected=the response is the sessions object or {}; attendance/session_archive is not written
  - An unauthenticated caller is rejected: expected=unauthenticated error
<<<
COMMENT: >>>
domain: Live Raid/Voice
notes: Disagreement: REQ-ROO-145 says GET /api/live-raid/history/all with no sessionId and without fields=full returns at most limit sessions (default 12, clamped to 1–50), newest endedAt first, and each default object has only id, eventTitle, eventDate, eventKey, endedAt, endedEarly, committedBy, totalPulses, expectedPulses, userTallies, commitments, and inGameStatus, with grids omitted; fields=full or a sessionId query returns the stored archive row. UNT-ROO-148 says an authenticated member receives the sessions object from attendance/session_archive, or {} when empty, and that the read is read-only. It does not state limit, clamp, endedAt order, a trend field subset, fields=full, or sessionId. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-145

[REQUIREMENT]
UID: TST-ROO-124
STATUS: Active
TITLE: DeleteLiveRaidArchive removes one archive leaf for an officer
STATEMENT: >>>
Plan: DeleteLiveRaidArchive removes one archive leaf for an officer
level: system
verifies: REQ-ROO-145, FNC-ROO-139, API-ROO-098, UNT-ROO-149, CMP-ROO-022
requires_tol: TOL-ROO-006
patterns: officer_delete_archive
execution_status: blocked_on_tooling
evidence_status: none
cases:
  - An officer delete removes that archive leaf: expected=attendance/session_archive/{sessionId} is removed
  - A non-officer delete does not count: expected=403; the archive leaf is not removed
<<<
COMMENT: >>>
domain: Live Raid/Voice
notes: Disagreement: REQ-ROO-145's published statement describes only the limited history GET. UNT-ROO-149 says an officer DELETE /api/live-raid/history/:sessionId removes attendance/session_archive/{sessionId}, that the route is officer-only, and that errors include 403 and 404. The unit does not state when 404 is returned. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-145

[REQUIREMENT]
UID: TST-ROO-125
STATUS: Active
TITLE: PatchArchivedInGameFlags stores or clears an archived in-game flag and does not change the Active session
STATEMENT: >>>
Plan: PatchArchivedInGameFlags stores or clears an archived in-game flag and does not change the Active session
level: system
verifies: REQ-ROO-145, FNC-ROO-140, API-ROO-099, UNT-ROO-150, CMP-ROO-022
requires_tol: TOL-ROO-006
patterns: in_game_flag_set, in_game_flag_clear, active_session_untouched
execution_status: blocked_on_tooling
evidence_status: none
cases:
  - confirmed true stores the in-game flag: expected=the flag is set at session_archive/{id}/inGameStatus/{userId}
  - confirmed false or any other value clears the flag: expected=the in-game flag at session_archive/{id}/inGameStatus/{userId} is cleared
  - A missing archive is 404: expected=404
  - A non-officer patch does not count: expected=403; the in-game flag is not changed
  - The Active live_session is not mutated: expected=the Active live_session is unchanged
<<<
COMMENT: >>>
domain: Live Raid/Voice
notes: Disagreement: REQ-ROO-145's published statement describes only the limited history GET. UNT-ROO-150 says an officer PATCH sets the in-game flag when confirmed is true and clears it when confirmed is false or other, returns 404 when the archive is missing, does not mutate the Active live_session, and lists errors 403, 404, and 400. The unit does not state when 400 is returned. Expected output follows the unit. verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-145

[REQUIREMENT]
UID: TST-ROO-126
STATUS: Active
TITLE: GvgHistoryAndOcrReviewSpa renders History and OCR Review routes and does not mint OCR HTTP
STATEMENT: >>>
Plan: GvgHistoryAndOcrReviewSpa renders History and OCR Review routes and does not mint OCR HTTP
level: unit
verifies: REQ-ROO-146, FNC-ROO-141, UNT-ROO-151, CMP-ROO-023
requires_tol: TOL-ROO-006
patterns: history_route, ocr_review_route, no_ocr_http
execution_status: blocked_on_tooling
evidence_status: none
cases:
  - The history path renders the history tab: expected=AttendanceHistoryTab is rendered
  - The OCR review path renders the OCR review tab: expected=OcrReviewTab is rendered
  - An OCR review id path renders the same OCR review tab: expected=OcrReviewTab is rendered
  - This unit does not count as an OCR HTTP writer: expected=no /api/ocr-reviews* HTTP API is provided
  - A failed game or billing gate does not render the tab: expected=redirect; History or OCR Review is not rendered
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-146

[REQUIREMENT]
UID: TST-ROO-127
STATUS: Active
TITLE: LiveRaidPageLoadOnce loads session reads on open or identity change and does not re-GET while the page stays open
STATEMENT: >>>
Plan: LiveRaidPageLoadOnce loads session reads on open or identity change and does not re-GET while the page stays open
level: unit
verifies: REQ-ROO-184, FNC-ROO-185, UNT-ROO-195, CMP-ROO-029
requires_tol: TOL-ROO-006
patterns: no_leave_open_reget, local_now_clock, history_limit_12
execution_status: blocked_on_tooling
evidence_status: none
cases:
  - Leaving the page open does not repeat those GETs: expected=no repeat GET of the live session, voice presence, published compositions, or commitments
  - Opening the page performs those loads: expected=loads of the live session, voice presence, published compositions, and commitments happen
  - A session identity change performs those loads again: expected=loads of the live session, voice presence, published compositions, and commitments happen again
  - The one-second local clock is not a server poll: expected=a 1-second local clock may update on-screen now; that clock is not a server poll
  - History on this page requests limit 12: expected=the request is /api/live-raid/history/all?limit=12
  - The card roster uses the card member view: expected=GET /api/attendance/members?view=card
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-184

[REQUIREMENT]
UID: TST-ROO-128
STATUS: Active
TITLE: AttendanceBeginRaidNoPresenceTicker stores active_session, replies Live Raid active, and does not start a voice tally
STATEMENT: >>>
Plan: AttendanceBeginRaidNoPresenceTicker stores active_session, replies Live Raid active, and does not start a voice tally
level: system
verifies: REQ-ROO-188, FNC-ROO-189, API-ROO-117, UNT-ROO-199, CMP-ROO-022
requires_tol: TOL-ROO-006
patterns: active_session_key, no_presence_ticker
execution_status: blocked_on_tooling
evidence_status: none
cases:
  - The session is stored at attendance/active_session and not at live_session: expected=the active attendance session is stored at attendance/active_session; it is not stored at attendance/live_session
  - The response message is Live Raid active.: expected=the response message is 'Live Raid active.'
  - A previous attendance interval ticker is cleared and not replaced: expected=that attendanceIntervalTicker is cleared and is not replaced
  - Begin-raid does not start a 15-minute voice tally: expected=no 15-minute interval starts that increments attendance/active_session user tallies from voice channels
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-188

[REQUIREMENT]
UID: TST-ROO-129
STATUS: Active
TITLE: LiveSessionWatchSkipIdleReads skips later live_session queries after the watch is absent and still archives while active and past end
STATEMENT: >>>
Plan: LiveSessionWatchSkipIdleReads skips later live_session queries after the watch is absent and still archives while active and past end
level: unit
verifies: REQ-ROO-193, FNC-ROO-194, UNT-ROO-204, CMP-ROO-022
requires_tol: TOL-ROO-006
patterns: watch_absent_skip, watch_active_archive, in_process_only
execution_status: blocked_on_tooling
evidence_status: none
cases:
  - The first read that does not find Active sets the watch absent: expected=the watch is set to absent
  - A read that finds Active sets the watch active: expected=the watch is set to active
  - Creating a live raid from published sets the watch active: expected=the watch is set to active
  - A war-room read that finds Active sets the watch active: expected=the watch is set to active
  - End or cancel sets the watch absent: expected=the watch is set to absent
  - Later ticks after absent do not query the live session: expected=that tick does not query attendance/live_session
  - An active watch past monitoringEndsAt archives and then marks absent: expected=the session is archived through endLiveRaidSessionInternal (the same path as officer End Raid), then the watch is marked absent
  - Another process is not visible to this watch: expected=the other process is not visible to this watch
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Watch reads come from the minute loop's live-session check, resolveLiveExists (games/ragnarok-origin/services/warRoomAutomation.js:135-144), per UNT-ROO-204 and FNC-ROO-194; there is no maybeAutoEndLiveRaid at f38e137 (removed in 9237b35, still absent). Case 7 follows the end-time check that exists today: at f38e137 it runs only in runPulseOnce (backend/src/api/liveRaid.routes.js:204-216, archive call L211), which runs only inside the pulse ticker (startTicker L290-322) armed by armMonitoringSchedule (L327-394), and at boot in resumeLiveRaidMonitoringIfNeeded (L426-435, archive call L431; called from backend/src/index.js:27-32). Both archive through endLiveRaidSessionInternal (L571-684), the same path as officer End Raid. endLiveRaidSessionInternal then marks the watch absent (noteLiveSessionCleared, L683; watch L397-410). The 60-second tick itself does not archive a past-end session (UNT-ROO-204 code gap vs REQ-ROO-193 criterion 2, with REQ-ROO-144), so while the pulse ticker is not running and the process does not restart nothing reaches case 7 at f38e137; that is a code gap, not a plan defect.
ssot_status: published
HONESTY: published plan only; not executed; no EVD.
<<<
RELATIONS:
- TYPE: Parent
  VALUE: REQ-ROO-193

[REQUIREMENT]
UID: TST-ROO-130
STATUS: Active
TITLE: VoiceMonitoringKeepsArmingTenant runs pulses under the tenant captured at arm time, or without a tenant when none was current
STATEMENT: >>>
Plan: VoiceMonitoringKeepsArmingTenant runs pulses under the tenant captured at arm time, or without a tenant when none was current
level: unit
verifies: REQ-ROO-195, FNC-ROO-196, UNT-ROO-206, CMP-ROO-022
requires_tol: TOL-ROO-006
patterns: tenant_captured_at_arm, run_with_tenant, stop_clears_ticker
execution_status: blocked_on_tooling
evidence_status: none
cases:
  - Arming captures the current tenant, including the delayed start: expected=that tenantId is captured at arm time
  - Interval pulses and the delayed start use that tenant: expected=the live session is read and written under that tenant via runWithTenant
  - No tenant at arm time does not use runWithTenant: expected=the tick runs without runWithTenant
  - A stop pulse still clears the interval ticker: expected=the interval ticker is cleared
<<<
COMMENT: >>>
domain: Live Raid/Voice
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-195

[[/SECTION]]

[[SECTION]]
TITLE: Attendance/Roster — TST-ROO-131 .. TST-ROO-146 (16 plans)

[REQUIREMENT]
UID: TST-ROO-131
STATUS: Active
TITLE: VanishRosterMembers purges roster leaves, enqueues non-dummy kicks without blocking, and rejects empty or over-cap batches
STATEMENT: >>>
Plan: VanishRosterMembers purges roster leaves, enqueues non-dummy kicks without blocking, and rejects empty or over-cap batches
level: system
verifies: REQ-ROO-101, FNC-ROO-076, API-ROO-048, UNT-ROO-086, CMP-ROO-014
requires_tol: TOL-ROO-006
patterns: purge_leaves, kick_enqueue_nonblocking, empty_or_over_cap
execution_status: blocked_on_tooling
evidence_status: none
cases:
  - Officer purge removes each target and enqueues a non-dummy kick without waiting: expected=auction/members/{uid} is removed for each target; a kick is queued for each non-dummy; the purge result and kick enqueue status are returned without waiting on kick completion
  - Duplicate targets are purged once: expected=that uid is purged once; the duplicate does not count as another purge
  - An empty batch does not count: expected=400 empty; no auction/members leaf is removed
  - A batch over 500 does not count: expected=400 over-cap; no auction/members leaf is removed
  - dummy_* is purged and is not Discord-kicked: expected=auction/members/{dummy uid} is removed; no Discord kick is queued for that dummy
  - Kicks are refused when the bot or circuit does not allow them: expected=503; kicks are refused and are not enqueued
  - A non-officer is rejected: expected=the call is rejected; no auction/members leaf is removed and no kick is queued
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-101

[REQUIREMENT]
UID: TST-ROO-132
STATUS: Active
TITLE: AtomicRosterLeafUpdate patches one member leaf and rejects a missing member or missing fields
STATEMENT: >>>
Plan: AtomicRosterLeafUpdate patches one member leaf and rejects a missing member or missing fields
level: system
verifies: REQ-ROO-102, FNC-ROO-077, API-ROO-049, UNT-ROO-087, CMP-ROO-014
requires_tol: TOL-ROO-006
patterns: atomic_leaf_patch, missing_member, missing_fields
execution_status: blocked_on_tooling
evidence_status: none
cases:
  - Officer patch stores the updates and returns that leaf: expected=auction/members/{targetUid} is atomically patched with those fields; the returned leaf view is that patched member
  - Missing targetUid or updates does not count: expected=400 missing fields; no member leaf is patched
  - A missing member is not patched: expected=404 missing member; no leaf is created or patched
  - A non-officer is rejected: expected=the call is rejected; no member leaf is patched
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-102

[REQUIREMENT]
UID: TST-ROO-133
STATUS: Active
TITLE: BulkRosterSaveBatch commits one multi-path roster write, seeds leave credits only when newly raid-rostered, and does not overwrite real Discord names
STATEMENT: >>>
Plan: BulkRosterSaveBatch commits one multi-path roster write, seeds leave credits only when newly raid-rostered, and does not overwrite real Discord names
level: system
verifies: REQ-ROO-103, FNC-ROO-078, API-ROO-050, UNT-ROO-088, CMP-ROO-014
requires_tol: TOL-ROO-006
patterns: atomic_batch, leave_seed_only_new, display_name_guard
execution_status: blocked_on_tooling
evidence_status: none
cases:
  - Officer batch stores the named roster fields in one atomic write: expected=those fields are stored for each uid in one atomic multi-path update; no partial apply; stored inGameName is at most 100 characters
  - Missing stagedMembers does not count: expected=400 missing stagedMembers; no roster leaves are written
  - A non-officer is rejected: expected=the call is rejected; no roster leaves are written
  - Newly raid-rostered members with unset credits get the leave-credit seed: expected=leaveCreditsRemaining is stored as defaultLeaveCredits and noConfirmCount is stored as 0
  - Members who are not newly raid-rostered or who already have credits are not seeded: expected=leave credits are not seeded and an existing noConfirmCount is not replaced by the seed
  - A dummy display name from the batch is stored: expected=that displayName is stored on the dummy leaf
  - A real Discord display name is not overwritten from the batch: expected=the stored Discord displayName is unchanged
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-103

[REQUIREMENT]
UID: TST-ROO-134
STATUS: Active
TITLE: CreateDummyRosterMember allocates the next dummy id and stores the default leaf
STATEMENT: >>>
Plan: CreateDummyRosterMember allocates the next dummy id and stores the default leaf
level: system
verifies: REQ-ROO-104, FNC-ROO-079, API-ROO-051, UNT-ROO-089, CMP-ROO-014
requires_tol: TOL-ROO-006
patterns: next_dummy_id, dummy_defaults, empty_name
execution_status: blocked_on_tooling
evidence_status: none
cases:
  - The next dummy id is allocated from existing dummy keys: expected=the created member id is the next sequential dummy_NNN after scanning existing dummy_* keys
  - The created leaf stores dummy defaults and is returned: expected=auction/members/dummy_NNN is stored with isDummy true, status Active, isRaidRoster false, leaveCreditsRemaining equal to defaultLeaveCredits, and noConfirmCount 0; that created member is returned
  - An empty display name does not count: expected=400 empty displayName; no dummy member is created
  - A non-officer is rejected: expected=the call is rejected; no dummy member is created
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-104

[REQUIREMENT]
UID: TST-ROO-135
STATUS: Active
TITLE: MemberProfileReader returns one profile for query and path uids, officer-gates non-self, and applies leave-credit defaults for display
STATEMENT: >>>
Plan: MemberProfileReader returns one profile for query and path uids, officer-gates non-self, and applies leave-credit defaults for display
level: system
verifies: REQ-ROO-105, FNC-ROO-080, API-ROO-052, API-ROO-053, UNT-ROO-090, CMP-ROO-014
requires_tol: TOL-ROO-006
patterns: query_and_path, self_or_officer, display_default
execution_status: blocked_on_tooling
evidence_status: none
cases:
  - Query uid and path uid share this reader for self: expected=both shapes return that member's profile from this reader
  - An officer can read another member: expected=that member's profile is returned
  - A non-officer reading someone else does not count: expected=the call is rejected; the other member's profile is not returned
  - A uid that is neither a snowflake nor dummy_* is rejected: expected=400 bad uid; no profile is returned
  - A missing member is not returned: expected=404; no profile is returned
  - A non-integer leave balance is defaulted for display: expected=the returned profile uses defaultLeaveCredits for leaveCreditsRemaining; the unit does not say that default is stored
  - An integer leave balance is returned as stored: expected=the returned leaveCreditsRemaining is that integer; the display default does not replace it
  - The profile includes the jobs, roles, and defaultLeaveCredits excerpt: expected=the returned profile includes the jobs, roles, and defaultLeaveCredits config excerpt
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-105

[REQUIREMENT]
UID: TST-ROO-136
STATUS: Active
TITLE: LeaveCreditsSelfSummary returns the signed-in member's credits, no-confirm count, and default, with fallbacks when values are not integers
STATEMENT: >>>
Plan: LeaveCreditsSelfSummary returns the signed-in member's credits, no-confirm count, and default, with fallbacks when values are not integers
level: system
verifies: REQ-ROO-106, FNC-ROO-081, API-ROO-054, UNT-ROO-091, CMP-ROO-014
requires_tol: TOL-ROO-006
patterns: self_scope, credit_fallback, no_confirm_default
execution_status: blocked_on_tooling
evidence_status: none
cases:
  - The signed-in member's integer summary is returned: expected=the summary is that member's leaveCreditsRemaining and noConfirmCount, plus defaultLeaveCredits; it is not another member's summary
  - A non-integer leave balance falls back to the configuration default: expected=returned leaveCreditsRemaining is defaultLeaveCredits; the unit does not say that fallback is stored
  - A non-integer no-confirm count falls back to 0: expected=returned noConfirmCount is 0; the unit does not say that 0 is stored
  - An unauthenticated caller is rejected: expected=the call is rejected as unauthenticated; no summary is returned
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-106

[REQUIREMENT]
UID: TST-ROO-137
STATUS: Active
TITLE: OfficerLeaveCreditDelta stores a clamped non-negative credit total and rejects a zero delta or a missing member
STATEMENT: >>>
Plan: OfficerLeaveCreditDelta stores a clamped non-negative credit total and rejects a zero delta or a missing member
level: system
verifies: REQ-ROO-107, FNC-ROO-082, API-ROO-055, UNT-ROO-092, CMP-ROO-014
requires_tol: TOL-ROO-006
patterns: clamped_delta, unset_uses_default, bad_delta
execution_status: blocked_on_tooling
evidence_status: none
cases:
  - A non-zero delta that stays at or above zero is stored: expected=stored leaveCreditsRemaining is current plus delta
  - A delta that would go below zero stores 0: expected=stored leaveCreditsRemaining is 0; a negative total is not stored
  - An unset balance uses defaultLeaveCredits as the current value, then stores the clamped sum: expected=the current value used for the sum is defaultLeaveCredits; the stored leaveCreditsRemaining is max(0, that current plus delta)
  - A zero or non-integer delta does not count: expected=400 bad delta; leaveCreditsRemaining is not changed
  - A missing member is not adjusted: expected=404; no leaveCreditsRemaining is written
  - A non-officer is rejected: expected=the call is rejected; leaveCreditsRemaining is not changed
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-107

[REQUIREMENT]
UID: TST-ROO-138
STATUS: Active
TITLE: BootSeedMissingLeaveCredits seeds unset credits for raid-roster non-Ghost members and does not overwrite an existing integer
STATEMENT: >>>
Plan: BootSeedMissingLeaveCredits seeds unset credits for raid-roster non-Ghost members and does not overwrite an existing integer
level: unit
verifies: REQ-ROO-108, FNC-ROO-083, UNT-ROO-093, CMP-ROO-014
requires_tol: TOL-ROO-006
patterns: seed_missing_only, skip_ghost, seeded_count
execution_status: blocked_on_tooling
evidence_status: none
cases:
  - An eligible member with a non-integer balance is seeded: expected=leaveCreditsRemaining is stored as defaultLeaveCredits and noConfirmCount is stored as 0
  - A missing defaultLeaveCredits stores 3: expected=leaveCreditsRemaining is stored as 3
  - An existing integer balance is not overwritten: expected=that integer leaveCreditsRemaining is unchanged
  - An existing noConfirmCount is not reset: expected=noConfirmCount is not stored as 0 by this seed
  - Ghost and non-raid members do not count: expected=that member is not seeded
  - A tenant that is not onboarded does not count: expected=that tenant's member is not seeded
  - The result is the seeded member count per tenant: expected=the output is the seeded member count per tenant
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-108

[REQUIREMENT]
UID: TST-ROO-139
STATUS: Active
TITLE: MonthlyLeaveCreditRefresh resets raid-roster credits on guild day 1 once per year-month and skips otherwise
STATEMENT: >>>
Plan: MonthlyLeaveCreditRefresh resets raid-roster credits on guild day 1 once per year-month and skips otherwise
level: unit
verifies: REQ-ROO-109, FNC-ROO-084, UNT-ROO-094, CMP-ROO-014
requires_tol: TOL-ROO-006
patterns: day1_reset, marker_once, skip_ineligible
execution_status: blocked_on_tooling
evidence_status: none
cases:
  - Day 1 with no marker resets eligible leave credits: expected=leaveCreditsRemaining is stored as defaultLeaveCredits; the refresh ran
  - Ghost and non-raid members are not reset: expected=that member's leaveCreditsRemaining is not reset
  - A day that is not guild day 1 does not count: expected=refresh is skipped; leave credits are not reset; the ym marker is not written
  - An existing year-month marker does not count as another refresh: expected=refresh is skipped; leave credits are not reset again
  - A run stores the year-month marker: expected=attendance/leave_credit_refresh/{ym} is stored with ranAt, defaultCredits, and count
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-109

[REQUIREMENT]
UID: TST-ROO-140
STATUS: Active
TITLE: OfficerJobDesiredCount stores a job desiredCount and stores 0 when the value does not parse
STATEMENT: >>>
Plan: OfficerJobDesiredCount stores a job desiredCount and stores 0 when the value does not parse
level: system
verifies: REQ-ROO-111, FNC-ROO-087, API-ROO-058, UNT-ROO-095, CMP-ROO-014
requires_tol: TOL-ROO-006
patterns: desired_count_stored, unparsable_zero, missing_job
execution_status: blocked_on_tooling
evidence_status: none
cases:
  - A parsable desiredCount is stored for the job: expected=settings/configuration/jobs/{jobCode}/desiredCount is stored as that integer; the saved desiredCount is returned
  - An unparsable desiredCount is stored as 0: expected=settings/configuration/jobs/{jobCode}/desiredCount is stored as 0
  - A missing jobCode does not count: expected=400 missing jobCode; no desiredCount is stored
  - A non-officer is rejected: expected=the call is rejected; no desiredCount is stored
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-111

[REQUIREMENT]
UID: TST-ROO-141
STATUS: Active
TITLE: OfficerExpectedAttendanceRate stores a rate clamped to 0–100 and rejects a non-numeric rate
STATEMENT: >>>
Plan: OfficerExpectedAttendanceRate stores a rate clamped to 0–100 and rejects a non-numeric rate
level: system
verifies: REQ-ROO-112, FNC-ROO-088, API-ROO-059, UNT-ROO-096, CMP-ROO-014
requires_tol: TOL-ROO-006
patterns: rate_clamped, in_range_stored, non_numeric
execution_status: blocked_on_tooling
evidence_status: none
cases:
  - A rate inside 0–100 is stored as given: expected=settings/configuration/expectedAttendanceRate is stored as that number
  - A rate outside 0–100 is clamped: expected=the saved rate is 0 when the input is below 0 and 100 when the input is above 100
  - A non-numeric rate does not count: expected=400 non-numeric; expectedAttendanceRate is not saved
  - A non-officer is rejected: expected=the call is rejected; expectedAttendanceRate is not saved
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-112

[REQUIREMENT]
UID: TST-ROO-142
STATUS: Active
TITLE: PeakHoursHeatmapAggregate builds the heatmap from raid-roster schedules and returns missing only to officers
STATEMENT: >>>
Plan: PeakHoursHeatmapAggregate builds the heatmap from raid-roster schedules and returns missing only to officers
level: system
verifies: REQ-ROO-110, FNC-ROO-085, API-ROO-056, UNT-ROO-097, CMP-ROO-015
requires_tol: TOL-ROO-006
patterns: eligible_aggregate, timezone_default, officer_missing
execution_status: blocked_on_tooling
evidence_status: none
cases:
  - An authenticated member receives the heatmap aggregate: expected=the response includes timezone, mine, heatmap, peak, and filled/total built from those eligible playSchedules
  - Dummy and non-raid members do not count: expected=dummy and non-raid members are excluded from the aggregate
  - A missing configuration timezone uses Asia/Manila: expected=returned timezone is Asia/Manila
  - An officer receives the missing list: expected=the response includes missing as a list
  - A non-officer missing list does not count: expected=missing is []
  - An unauthenticated caller is rejected: expected=the call is rejected as unauthenticated; no heatmap is returned
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-110

[REQUIREMENT]
UID: TST-ROO-143
STATUS: Active
TITLE: SaveOwnPlaySchedule stores the caller's schedule when it has at least one hour and rejects dummies, missing roster members, and empty hours
STATEMENT: >>>
Plan: SaveOwnPlaySchedule stores the caller's schedule when it has at least one hour and rejects dummies, missing roster members, and empty hours
level: system
verifies: REQ-ROO-110, FNC-ROO-086, API-ROO-057, UNT-ROO-098, CMP-ROO-015
requires_tol: TOL-ROO-006
patterns: self_schedule, min_one_hour, reject_dummy
execution_status: blocked_on_tooling
evidence_status: none
cases:
  - A Discord member on the roster stores their own schedule: expected=auction/members/{caller uid}/playSchedule is stored as that normalized schedule
  - A dummy caller does not count: expected=400 dummy; no playSchedule is written
  - A caller who is not on the roster is rejected: expected=404 not on roster; no playSchedule is written
  - Fewer than one play hour does not count: expected=400; the schedule is rejected and playSchedule is not written
  - An unauthenticated caller is rejected: expected=the call is rejected as unauthenticated; no playSchedule is written
  - The write is self-only: expected=the stored playSchedule is the caller's auction/members/{caller uid}/playSchedule, not another member's
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-110

[REQUIREMENT]
UID: TST-ROO-144
STATUS: Active
TITLE: AttendanceSpaRoutes renders MasterList, Profile, Peak Hours, and Statistics under /attendance and does not mount the other surfaces
STATEMENT: >>>
Plan: AttendanceSpaRoutes renders MasterList, Profile, Peak Hours, and Statistics under /attendance and does not mount the other surfaces
level: unit
verifies: REQ-ROO-113, FNC-ROO-089, UNT-ROO-099, CMP-ROO-016
requires_tol: TOL-ROO-006
patterns: attendance_routes, profile_uid, out_of_batch
execution_status: blocked_on_tooling
evidence_status: none
cases:
  - Master List is the masterlist route: expected=the rendered attendance tab is MasterList
  - Profile is both the self route and the uid route: expected=both paths render Profile
  - Peak Hours is the peak-hours route: expected=the rendered attendance tab is Peak Hours
  - Statistics is the statistics route: expected=the rendered attendance tab is Statistics
  - Scheduler, War Room, Raid, OCR, and History do not count: expected=this unit does not render those surfaces
  - These routes stay out of the shell: expected=the attendance tab is rendered by this unit and is not folded into the shell; the shell keeps apiClient and nav only
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-113

[REQUIREMENT]
UID: TST-ROO-145
STATUS: Active
TITLE: MasterListCarouselChevrons keeps the chevron row stable by sizing to the cap and truncating the visible title
STATEMENT: >>>
Plan: MasterListCarouselChevrons keeps the chevron row stable by sizing to the cap and truncating the visible title
level: unit
verifies: REQ-ROO-173, FNC-ROO-174, UNT-ROO-184, CMP-ROO-016
requires_tol: TOL-ROO-006
patterns: roster_sizer_cap, invisible_labels, stable_chevrons
execution_status: blocked_on_tooling
evidence_status: none
cases:
  - The roster sizer uses the max of the active count and ROSTER_CAP, not the live count alone: expected=the sizer label uses 200 when the active count is below 200, and uses the active count when the active count is above 200
  - Invisible copies of every slide label share the visible title's grid cell: expected=invisible copies of every slide label occupy the same grid cell as the visible title
  - The visible heading is the current slide title and truncates: expected=the visible heading is the current slide title; the roster heading includes the live active count and the cap; the heading truncates instead of widening the chevron row
  - Switching slides does not move the chevrons: expected=the chevron row horizontal position stays stable
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-173

[REQUIREMENT]
UID: TST-ROO-146
STATUS: Active
TITLE: CardRosterMemberView returns card fields or the stored roster and rejects a missing session
STATEMENT: >>>
Plan: CardRosterMemberView returns card fields or the stored roster and rejects a missing session
level: system
verifies: REQ-ROO-187, FNC-ROO-188, API-ROO-116, UNT-ROO-198, CMP-ROO-014
requires_tol: TOL-ROO-006
patterns: card_fields, stored_roster, session_401
execution_status: blocked_on_tooling
evidence_status: none
cases:
  - view=card returns only the four card fields: expected=the response is one object per roster member containing only uid, displayName, jobCode, and isRaidRoster
  - isRaidRoster is true only when the stored flag is true: expected=the card row is isRaidRoster true only for the member whose stored flag is true; the other member does not count as isRaidRoster true
  - No view returns the stored roster objects: expected=the response is the stored roster objects, not the card field subset
  - An unauthenticated caller is rejected: expected=401 for both
<<<
COMMENT: >>>
domain: Attendance/Roster
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-187

[[/SECTION]]

[[SECTION]]
TITLE: Raid compose/Party — TST-ROO-147 .. TST-ROO-175 (29 plans)

[REQUIREMENT]
UID: TST-ROO-147
STATUS: Active
TITLE: ListRaidCompositions returns a normalized compositions map, persists a legacy migration, and rejects an unauthenticated caller
STATEMENT: >>>
Plan: ListRaidCompositions returns a normalized compositions map, persists a legacy migration, and rejects an unauthenticated caller
level: system
verifies: REQ-ROO-123, FNC-ROO-102, API-ROO-069, UNT-ROO-112, CMP-ROO-019
requires_tol: TOL-ROO-006
patterns: normalized_map, empty_store, legacy_migrate, no_rewrite
execution_status: blocked_on_tooling
evidence_status: none
cases:
  - Each config in the returned map is normalized: expected=the returned compositions map has each config normalized with tabs, tabOrder, and gridTopology
  - An empty store returns an empty object: expected={}
  - A needed legacy migration is persisted: expected=the normalized document is persisted back
  - A composition that does not need migration is not rewritten: expected=those documents are not rewritten
  - An unauthenticated caller is rejected: expected=unauthenticated; no compositions map is returned
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-123

[REQUIREMENT]
UID: TST-ROO-148
STATUS: Active
TITLE: CreateBlankRaidComposition allocates the next raid_NNN and seeds one Main 8x5 tab
STATEMENT: >>>
Plan: CreateBlankRaidComposition allocates the next raid_NNN and seeds one Main 8x5 tab
level: system
verifies: REQ-ROO-123, FNC-ROO-103, API-ROO-070, UNT-ROO-113, CMP-ROO-019
requires_tol: TOL-ROO-006
patterns: raid_nnn, main_tab, default_title, audit_fields
execution_status: blocked_on_tooling
evidence_status: none
cases:
  - The new id is the next raid_NNN: expected=the created document id is the next sequential raid_NNN from those keys
  - The blank config starts with one Main tab: expected=tab_001 is named Main, slots_allocation is empty, tabOrder is [tab_001], and the topology is 8x5
  - A default title is stored: expected=the created composition stores a default title
  - lastUpdated and updatedBy are recorded: expected=lastUpdated and updatedBy are recorded on the new document
  - A non-officer is rejected: expected=the call is rejected; no attendance/compositions/raid_NNN document is created
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-123

[REQUIREMENT]
UID: TST-ROO-149
STATUS: Active
TITLE: SaveRaidCompositionTabs replaces the document after the cross-tab check and rejects duplicates
STATEMENT: >>>
Plan: SaveRaidCompositionTabs replaces the document after the cross-tab check and rejects duplicates
level: system
verifies: REQ-ROO-123, FNC-ROO-104, API-ROO-071, UNT-ROO-114, CMP-ROO-019
requires_tol: TOL-ROO-006
patterns: persist_strip_legacy, audit_fields, duplicates_rejected
execution_status: blocked_on_tooling
evidence_status: none
cases:
  - A save with no duplicates replaces the document and removes legacy root slots: expected=attendance/compositions/{configId} is replaced via compositionForPersist; legacy root slots_allocation is removed
  - lastUpdated and updatedBy are recorded on save: expected=lastUpdated and updatedBy are recorded
  - Duplicates do not count and are not persisted: expected=400 duplicates with the duplicates list; the document is not replaced
  - A non-officer is rejected: expected=the call is rejected; the composition document is not replaced
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-123

[REQUIREMENT]
UID: TST-ROO-150
STATUS: Active
TITLE: DuplicateRaidComposition copies into a new raid_NNN with a (Copy) title and preserves topology
STATEMENT: >>>
Plan: DuplicateRaidComposition copies into a new raid_NNN with a (Copy) title and preserves topology
level: system
verifies: REQ-ROO-123, FNC-ROO-105, API-ROO-072, UNT-ROO-115, CMP-ROO-019
requires_tol: TOL-ROO-006
patterns: copy_title, topology, clean_override, missing_source
execution_status: blocked_on_tooling
evidence_status: none
cases:
  - The duplicate gets a new raid_NNN and a (Copy) title: expected=a new raid_NNN is stored; the title is the source title with suffix (Copy)
  - gridTopology is preserved: expected=the duplicate gridTopology is the source topology
  - A clean payload overrides copied slots: expected=the copied slots are that clean override, not the source slots
  - Without a clean payload the source slots are copied: expected=the source slots are copied; they are not replaced by an override
  - updatedBy and lastUpdated are recorded on the duplicate: expected=updatedBy and lastUpdated are recorded on the new document
  - A missing source does not count: expected=404; no new raid_NNN is stored
  - A non-officer is rejected: expected=the call is rejected; no new raid_NNN is stored
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-123

[REQUIREMENT]
UID: TST-ROO-151
STATUS: Active
TITLE: DeleteRaidComposition removes the composition document and does not delete published snapshots
STATEMENT: >>>
Plan: DeleteRaidComposition removes the composition document and does not delete published snapshots
level: system
verifies: REQ-ROO-123, FNC-ROO-106, API-ROO-073, UNT-ROO-116, CMP-ROO-019
requires_tol: TOL-ROO-006
patterns: remove_composition, published_kept
execution_status: blocked_on_tooling
evidence_status: none
cases:
  - The composition document is removed: expected=attendance/compositions/{id} is removed
  - Published snapshots are not auto-deleted: expected=those published snapshots are not deleted
  - A non-officer is rejected: expected=the call is rejected; the composition document remains
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-123

[REQUIREMENT]
UID: TST-ROO-152
STATUS: Active
TITLE: CrossTabUniqueMembers reports a userId in more than one tab or in multiple coords and ignores a single placement
STATEMENT: >>>
Plan: CrossTabUniqueMembers reports a userId in more than one tab or in multiple coords and ignores a single placement
level: unit
verifies: REQ-ROO-124, FNC-ROO-107, UNT-ROO-117, CMP-ROO-019
requires_tol: TOL-ROO-006
patterns: single_placement, cross_tab, multi_coord
execution_status: blocked_on_tooling
evidence_status: none
cases:
  - A single placement does not count: expected=duplicates is empty
  - A userId on more than one tab is a duplicate: expected=duplicates contains one entry {userId, placements[]} for those placements
  - Multiple coords for one userId are a duplicate: expected=that userId is a duplicate entry {userId, placements[]}; it does not count as unique
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-124

[REQUIREMENT]
UID: TST-ROO-153
STATUS: Active
TITLE: GetActiveComposeSession returns the active session or null and does not create one
STATEMENT: >>>
Plan: GetActiveComposeSession returns the active session or null and does not create one
level: system
verifies: REQ-ROO-125, FNC-ROO-108, API-ROO-074, UNT-ROO-118, CMP-ROO-019
requires_tol: TOL-ROO-006
patterns: active_session, null_session, no_create
execution_status: blocked_on_tooling
evidence_status: none
cases:
  - The active key resolves to that compose session: expected=that compose session is returned
  - No active key returns null and is not an error: expected=session is null; that result is success, not an error
  - A missing active key does not create a session: expected=no attendance/compose document is created
  - An unauthenticated caller is rejected: expected=unauthenticated; no session is created
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-125

[REQUIREMENT]
UID: TST-ROO-154
STATUS: Active
TITLE: CreateComposeSession stores {eventDate}_{eventKey}, builds grids from the composition, and 404s a missing config
STATEMENT: >>>
Plan: CreateComposeSession stores {eventDate}_{eventKey}, builds grids from the composition, and 404s a missing config
level: system
verifies: REQ-ROO-125, FNC-ROO-109, API-ROO-075, UNT-ROO-119, CMP-ROO-019
requires_tol: TOL-ROO-006
patterns: session_id, grids_from_composition, missing_config
execution_status: blocked_on_tooling
evidence_status: none
cases:
  - The session id and compose_active are stored: expected=the session is stored at attendance/compose/{eventDate}_{eventKey} and compose_active is set to that session
  - Grids are built from the composition: expected=grids and selectedGridIds are the result of buildLiveGridsFromComposition for that config
  - A missing raid config does not count: expected=404; no compose session is stored and compose_active is not set
  - A non-officer is rejected: expected=the call is rejected; no compose session is stored
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-125

[REQUIREMENT]
UID: TST-ROO-155
STATUS: Active
TITLE: SaveComposeSessionGrids updates grids and audit fields and does not move compose_active
STATEMENT: >>>
Plan: SaveComposeSessionGrids updates grids and audit fields and does not move compose_active
level: system
verifies: REQ-ROO-125, FNC-ROO-110, API-ROO-076, UNT-ROO-120, CMP-ROO-019
requires_tol: TOL-ROO-006
patterns: grids_updated, audit_fields, active_unchanged
execution_status: blocked_on_tooling
evidence_status: none
cases:
  - The session grids are updated: expected=attendance/compose/{sessionId} grids are updated to those grids
  - lastUpdated and updatedBy are updated: expected=lastUpdated and updatedBy on that session are updated
  - compose_active is not changed: expected=the compose_active pointer is not changed
  - A non-officer is rejected: expected=the call is rejected; session grids are not updated
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-125

[REQUIREMENT]
UID: TST-ROO-156
STATUS: Active
TITLE: CloseComposeSession clears compose_active and keeps historical compose documents
STATEMENT: >>>
Plan: CloseComposeSession clears compose_active and keeps historical compose documents
level: system
verifies: REQ-ROO-125, FNC-ROO-111, API-ROO-077, UNT-ROO-121, CMP-ROO-019
requires_tol: TOL-ROO-006
patterns: clear_active, history_kept
execution_status: blocked_on_tooling
evidence_status: none
cases:
  - compose_active is removed: expected=attendance/compose_active is removed
  - Historical compose documents are not deleted: expected=those documents stay; they are not deleted
  - A non-officer is rejected: expected=the call is rejected; compose_active remains
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-125

[REQUIREMENT]
UID: TST-ROO-157
STATUS: Active
TITLE: SendComposeToPublished writes the event shell, keeps existing grids, and auto-anchors only when unset
STATEMENT: >>>
Plan: SendComposeToPublished writes the event shell, keeps existing grids, and auto-anchors only when unset
level: system
verifies: REQ-ROO-125, FNC-ROO-112, API-ROO-078, UNT-ROO-122, CMP-ROO-019
requires_tol: TOL-ROO-006
patterns: published_shell, empty_unless_existing, auto_anchor
execution_status: blocked_on_tooling
evidence_status: none
cases:
  - The published id is {eventDate}_{eventKey}: expected=attendance/published/{eventDate}_{eventKey} is written
  - A new shell has empty grids: expected=the published shell grids are empty
  - Existing grids are not replaced with empty: expected=those grids are kept
  - The first publish auto-anchors when the anchor is unset: expected=attendance/published_anchor is set
  - An anchor that is already set is not changed: expected=published_anchor is not changed
  - A missing configuration event does not count: expected=404 event missing; no published snapshot is written
  - A non-officer is rejected: expected=the call is rejected; no published snapshot is written
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-125

[REQUIREMENT]
UID: TST-ROO-158
STATUS: Active
TITLE: DeployComposeRosterToPublished writes the named or active session grids and rejects when no session exists
STATEMENT: >>>
Plan: DeployComposeRosterToPublished writes the named or active session grids and rejects when no session exists
level: system
verifies: REQ-ROO-125, FNC-ROO-113, API-ROO-079, UNT-ROO-123, CMP-ROO-019
requires_tol: TOL-ROO-006
patterns: named_session, active_session, no_session
execution_status: blocked_on_tooling
evidence_status: none
cases:
  - A named session's grids are published: expected=writePublishedSnapshot writes that session's grids
  - An omitted sessionId uses compose_active: expected=that active session is the one published
  - No compose session does not count: expected=400 no session; no published snapshot is written
  - A non-officer is rejected: expected=the call is rejected; no published snapshot is written
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-125

[REQUIREMENT]
UID: TST-ROO-159
STATUS: Active
TITLE: ListPublishedCompositions returns the published map and the anchor, including a null anchor
STATEMENT: >>>
Plan: ListPublishedCompositions returns the published map and the anchor, including a null anchor
level: system
verifies: REQ-ROO-126, FNC-ROO-114, API-ROO-080, UNT-ROO-124, CMP-ROO-019
requires_tol: TOL-ROO-006
patterns: published_map, anchor, read_only
execution_status: blocked_on_tooling
evidence_status: none
cases:
  - The response is the attendance/published map: expected=the response is that attendance/published map; it is not limited to the current raid-cycle published id plus an ids query
  - The anchor is returned and may be null: expected=the response includes attendance/published_anchor; null is a successful anchor value
  - The list does not write published data: expected=attendance/published and published_anchor are not written
  - An unauthenticated caller is rejected: expected=unauthenticated; no published map is returned
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-126

[REQUIREMENT]
UID: TST-ROO-160
STATUS: Active
TITLE: SetPublishedActiveAnchor sets the anchor, clears it only when it matches, and 404s a missing published id
STATEMENT: >>>
Plan: SetPublishedActiveAnchor sets the anchor, clears it only when it matches, and 404s a missing published id
level: system
verifies: REQ-ROO-126, FNC-ROO-115, API-ROO-081, UNT-ROO-125, CMP-ROO-019
requires_tol: TOL-ROO-006
patterns: anchor_set, anchor_clear_match, missing_published
execution_status: blocked_on_tooling
evidence_status: none
cases:
  - active true sets the anchor to that id: expected=published_anchor is that id
  - active false clears the anchor when it matches: expected=published_anchor is cleared
  - active false does not clear a different anchor: expected=published_anchor is not cleared
  - A missing published id does not count: expected=404; published_anchor is not updated
  - A non-officer is rejected: expected=the call is rejected; published_anchor is not updated
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-126

[REQUIREMENT]
UID: TST-ROO-161
STATUS: Active
TITLE: DeletePublishedComposition removes the snapshot and clears the anchor only when it matches
STATEMENT: >>>
Plan: DeletePublishedComposition removes the snapshot and clears the anchor only when it matches
level: system
verifies: REQ-ROO-126, FNC-ROO-116, API-ROO-082, UNT-ROO-126, CMP-ROO-019
requires_tol: TOL-ROO-006
patterns: remove_published, anchor_match, anchor_kept
execution_status: blocked_on_tooling
evidence_status: none
cases:
  - The published snapshot is removed: expected=attendance/published/{id} is removed
  - A matching anchor is cleared: expected=published_anchor is cleared
  - A different anchor is not cleared: expected=published_anchor is left in place
  - A non-officer is rejected: expected=the call is rejected; the published document remains
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-126

[REQUIREMENT]
UID: TST-ROO-162
STATUS: Active
TITLE: AddConfigGridsToPublished merges one config's live grids and leaves unrelated grids in place
STATEMENT: >>>
Plan: AddConfigGridsToPublished merges one config's live grids and leaves unrelated grids in place
level: system
verifies: REQ-ROO-128, FNC-ROO-119, API-ROO-085, UNT-ROO-127, CMP-ROO-019
requires_tol: TOL-ROO-006
patterns: merge_grids, unrelated_kept, missing_404
execution_status: blocked_on_tooling
evidence_status: none
cases:
  - The config's live grids are merged into the published snapshot: expected=buildLiveGridsFromComposition for that config is merged into the published grids and selectedGridIds
  - Unrelated grids are not deleted: expected=those unrelated grids remain
  - A missing published snapshot or raid config does not count: expected=404; no merge is written
  - A non-officer is rejected: expected=the call is rejected; published grids are not changed
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-128

[REQUIREMENT]
UID: TST-ROO-163
STATUS: Active
TITLE: RemoveConfigGridsFromPublished removes that config's grids and rejects a missing or invalid target
STATEMENT: >>>
Plan: RemoveConfigGridsFromPublished removes that config's grids and rejects a missing or invalid target
level: system
verifies: REQ-ROO-128, FNC-ROO-120, API-ROO-086, UNT-ROO-128, CMP-ROO-019
requires_tol: TOL-ROO-006
patterns: remove_config, missing_or_invalid
execution_status: blocked_on_tooling
evidence_status: none
cases:
  - That configId's grids are removed: expected=that configId's grids are removed from the published snapshot
  - Missing or invalid does not remove grids: expected=404 or 400, and the unit does not say which; grids are not removed
  - A non-officer is rejected: expected=the call is rejected; published grids are not changed
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-128

[REQUIREMENT]
UID: TST-ROO-164
STATUS: Active
TITLE: SavePublishedGrids replaces the grids map and rejects a missing published id or invalid grids
STATEMENT: >>>
Plan: SavePublishedGrids replaces the grids map and rejects a missing published id or invalid grids
level: system
verifies: REQ-ROO-128, FNC-ROO-121, API-ROO-087, UNT-ROO-129, CMP-ROO-019
requires_tol: TOL-ROO-006
patterns: full_replace, missing_or_invalid
execution_status: blocked_on_tooling
evidence_status: none
cases:
  - body.grids replaces the published grids map: expected=attendance/published/{id}/grids is replaced by body.grids; it is not a merge
  - A missing published snapshot or invalid grids do not replace the map: expected=404 or 400, and the unit does not say which; grids are not replaced
  - A non-officer is rejected: expected=the call is rejected; published grids are not changed
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-128

[REQUIREMENT]
UID: TST-ROO-165
STATUS: Active
TITLE: AnnouncePublishedAttendanceCard builds the attendance announce from the published event and 404s a missing id
STATEMENT: >>>
Plan: AnnouncePublishedAttendanceCard builds the attendance announce from the published event and 404s a missing id
level: system
verifies: REQ-ROO-127, FNC-ROO-117, API-ROO-083, UNT-ROO-130, CMP-VAL-011
requires_tol: TOL-ROO-006
patterns: announce_fields, discord_send, missing_published
execution_status: blocked_on_tooling
evidence_status: none
cases:
  - A missing published id does not send: expected=404; no Discord message is sent
  - The attendance announce is built from event fields: expected=the attendance announce payload is built from eventTitle, eventDate, and timeStart
  - A sendable channel posts the Discord message: expected=a Discord message is sent through that helper and the send result is returned
  - A channel or bot failure is mapped without a per-code split: expected=the failure is 400, 404, or 503; the unit does not say which code; there is no successful send result
  - A non-officer is rejected: expected=the call is rejected; no Discord message is sent
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-127

[REQUIREMENT]
UID: TST-ROO-166
STATUS: Active
TITLE: AnnouncePublishedPartyCard builds the party announce from event title and date and 404s a missing id
STATEMENT: >>>
Plan: AnnouncePublishedPartyCard builds the party announce from event title and date and 404s a missing id
level: system
verifies: REQ-ROO-127, FNC-ROO-118, API-ROO-084, UNT-ROO-131, CMP-VAL-011
requires_tol: TOL-ROO-006
patterns: party_fields, discord_send, missing_published
execution_status: blocked_on_tooling
evidence_status: none
cases:
  - A missing published id does not send: expected=404; no Discord message is sent
  - The party announce is built from event title and date: expected=the party-ready announce payload is built from eventTitle and eventDate
  - A sendable channel posts the Discord message: expected=a Discord message is sent through the gen-room helper and the send result is returned
  - A channel or bot failure is mapped without a per-code split: expected=the failure is 400, 404, or 503; the unit does not say which code; there is no successful send result
  - A non-officer is rejected: expected=the call is rejected; no Discord message is sent
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-127

[REQUIREMENT]
UID: TST-ROO-167
STATUS: Active
TITLE: WarRoomInitHubSnapshot joins the hub and does not write the sources it reads
STATEMENT: >>>
Plan: WarRoomInitHubSnapshot joins the hub and does not write the sources it reads
level: system
verifies: REQ-ROO-129, FNC-ROO-122, API-ROO-088, UNT-ROO-132, CMP-ROO-020
requires_tol: TOL-ROO-006
patterns: cycle_status, published_leaf, config_title, read_only
execution_status: blocked_on_tooling
evidence_status: none
cases:
  - An unauthenticated caller is rejected: expected=unauthenticated; no hub snapshot is returned
  - Raid cycle status is the computed cycle: expected=the snapshot raid cycle status is getRaidCycleStatus
  - The snapshot joins the named hub sources: expected=the snapshot joins settings/configuration, auction/members, attendance commitments, the live session, war_room_status, compositions, and listPublished
  - publishedRecord is the cycle.publishedId leaf when that leaf is present: expected=publishedRecord is that leaf
  - configTitle falls back to the compositions title: expected=configTitle is that compositions title
  - War rooms, automation, and channel ids are included: expected=the snapshot includes the war rooms catalog and selection, automation status, and resolved Discord war-room channel ids
  - The init read does not write joined sources: expected=auction/members, attendance commitments, compositions, and the live session are not written
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-129

[REQUIREMENT]
UID: TST-ROO-168
STATUS: Active
TITLE: AutoCreateLiveRaidFromPublished creates an in-process live raid only when the launch checks pass
STATEMENT: >>>
Plan: AutoCreateLiveRaidFromPublished creates an in-process live raid only when the launch checks pass
level: unit
verifies: REQ-ROO-130, FNC-ROO-123, UNT-ROO-133, CMP-ROO-020
requires_tol: TOL-ROO-006
patterns: in_process_create, skip, reject, war_room_status
execution_status: blocked_on_tooling
evidence_status: none
cases:
  - A ready phase-3 tick creates the live raid in-process: expected=a live raid is created in-process with launchedBy War Room; /api/live-raid/create is not called
  - Monitoring fields are taken from the cycle: expected=the created live raid stores those monitoring times and that pollIntervalMinutes
  - war_room_status records the outcome: expected=attendance/war_room_status is written with the outcome
  - needsSetup does not count: expected=skipped; no live raid is created
  - forceLocked does not count: expected=skipped; no live raid is created
  - No active event does not count: expected=skipped; no live raid is created
  - A phase other than 3 does not count: expected=skipped; no live raid is created
  - An existing live session is skipped: expected=skipped; no live raid is created
  - A duplicate live session is rejected by create: expected=rejected; no second live raid is created
  - Missing published or grids are rejected: expected=rejected; no live raid is created
  - Cross-tab duplicates are rejected: expected=rejected; no live raid is created
  - Unresolved war-room channels are rejected: expected=rejected; no live raid is created
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-130

[REQUIREMENT]
UID: TST-ROO-169
STATUS: Active
TITLE: WarRoomSpaSurface renders War Room and redirects legacy compose and liveraid paths
STATEMENT: >>>
Plan: WarRoomSpaSurface renders War Room and redirects legacy compose and liveraid paths
level: unit
verifies: REQ-ROO-131, FNC-ROO-124, UNT-ROO-134, CMP-ROO-021
requires_tol: TOL-ROO-006
patterns: war_room_route, compose_redirect, liveraid_redirect
execution_status: blocked_on_tooling
evidence_status: none
cases:
  - /attendance/war-room renders WarRoomTab: expected=WarRoomTab is rendered
  - /attendance/compose redirects to war-room: expected=navigate replace to /attendance/war-room
  - /attendance/liveraid redirects to war-room: expected=navigate replace to /attendance/war-room
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-131

[REQUIREMENT]
UID: TST-ROO-170
STATUS: Active
TITLE: RaidConfigSpaSurface renders RaidPartyTab only at /attendance/raidparty
STATEMENT: >>>
Plan: RaidConfigSpaSurface renders RaidPartyTab only at /attendance/raidparty
level: unit
verifies: REQ-ROO-132, FNC-ROO-125, UNT-ROO-135, CMP-ROO-021
requires_tol: TOL-ROO-006
patterns: raidparty_route, other_path
execution_status: blocked_on_tooling
evidence_status: none
cases:
  - /attendance/raidparty renders RaidPartyTab: expected=RaidPartyTab is rendered
  - Another path does not count as Raid Config: expected=RaidPartyTab is not rendered
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-132

[REQUIREMENT]
UID: TST-ROO-171
STATUS: Active
TITLE: NextUnfinishedWarCycle keeps an in-progress phase-3 war and otherwise walks at most three Monday-weeks
STATEMENT: >>>
Plan: NextUnfinishedWarCycle keeps an in-progress phase-3 war and otherwise walks at most three Monday-weeks
level: unit
verifies: REQ-ROO-175, FNC-ROO-176, UNT-ROO-186, CMP-ROO-020
requires_tol: TOL-ROO-006
patterns: ended, phase3_kept, three_weeks, prep_date
execution_status: blocked_on_tooling
evidence_status: none
cases:
  - Now at or before phase-3 timeEnd is not ended: expected=that occurrence is not treated as ended
  - Now strictly after phase-3 timeEnd is ended when not in phase 3: expected=that occurrence counts as ended
  - Phase 3 keeps the occurrence after its end: expected=that occurrence is kept
  - An occurrence beyond three Monday-weeks does not count: expected=warDate falls back to the war weekday in the current Monday-week; a later week does not count
  - A qualifying occurrence within three weeks is the warDate: expected=warDate is that occurrence
  - The phase-1 prep date is walked back from the chosen war date: expected=the phase-1 prep date is that war date walked backward, weekday wrap of 7, to the phase-1 weekday; it is not a separately shifted week
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-175

[REQUIREMENT]
UID: TST-ROO-172
STATUS: Active
TITLE: WarRoomLoadOnce loads init once and does not repeat init or voice presence while the page stays open
STATEMENT: >>>
Plan: WarRoomLoadOnce loads init once and does not repeat init or voice presence while the page stays open
level: unit
verifies: REQ-ROO-182, FNC-ROO-183, UNT-ROO-193, CMP-ROO-021
requires_tol: TOL-ROO-006
patterns: no_reget, no_voice_poll, load_once, match_304
execution_status: blocked_on_tooling
evidence_status: none
cases:
  - Leaving War Room open does not repeat init: expected=GET /api/war-room/init is not repeated
  - Leaving War Room open does not repeat the voice-presence poll: expected=the voice-presence poll is not repeated
  - Opening the page loads init once for a signed-in user: expected=init loads once
  - A matching If-None-Match may return 304: expected=init may return 304
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-182

[REQUIREMENT]
UID: TST-ROO-173
STATUS: Active
TITLE: CompositionListOmitGrids returns slim id and title rows only when fields=list and id is absent
STATEMENT: >>>
Plan: CompositionListOmitGrids returns slim id and title rows only when fields=list and id is absent
level: unit
verifies: REQ-ROO-186, FNC-ROO-187, UNT-ROO-197, CMP-ROO-019
requires_tol: TOL-ROO-006
patterns: slim_list, title_default, id_full, neither
execution_status: blocked_on_tooling
evidence_status: none
cases:
  - fields=list with no id returns id and title only: expected=every config is {id, title} only; no grids and no slot maps
  - A missing title defaults to the empty string: expected=that row's title is the empty string
  - An id returns that one full composition: expected=that one full composition is returned
  - fields=list does not apply when id is present: expected=the response is that one full composition; fields=list does not slim it
  - A missing id returns an empty compositions object: expected=the compositions object is empty
  - Neither id nor fields=list returns full compositions: expected=full compositions are returned
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-ROO-186

[REQUIREMENT]
UID: TST-ROO-174
STATUS: Active
TITLE: WarRoomPublishAssignedRaidParty syncs only the assigned config and leaves phase-3 Active snapshots alone
STATEMENT: >>>
Plan: WarRoomPublishAssignedRaidParty syncs only the assigned config and leaves phase-3 Active snapshots alone
level: unit
verifies: REQ-ROO-191, FNC-ROO-192, UNT-ROO-202, CMP-ROO-020
requires_tol: TOL-ROO-006
patterns: missing_config, phase_gate, strip_others, anchor_exact
execution_status: blocked_on_tooling
evidence_status: none
cases:
  - A missing assigned config fails publish: expected=publish fails with 'No Raid Party config is assigned in Game Settings.'; the published snapshot is not changed
  - Phase 1 or 2 still syncs when an Active live session exists: expected=sync runs
  - Phase 3 with no Active live session syncs: expected=sync runs
  - Phase 3 with an Active live session leaves the snapshot alone: expected=the published snapshot is left alone; configs are not added or removed
  - A successful sync keeps only the assigned config: expected=grids contain only that Raid Party config; the other configs on that published id are removed
  - Already holding exactly that config still sets the anchor active: expected=the published anchor is set active
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-191

[REQUIREMENT]
UID: TST-ROO-175
STATUS: Active
TITLE: WarRoomRepublishAndLiveStartOnce skips a repeated cycle key and records the live-start key only after a non-empty room list
STATEMENT: >>>
Plan: WarRoomRepublishAndLiveStartOnce skips a repeated cycle key and records the live-start key only after a non-empty room list
level: unit
verifies: REQ-ROO-192, FNC-ROO-193, UNT-ROO-203, CMP-ROO-020
requires_tol: TOL-ROO-006
patterns: cycle_key, skip_publish, live_start_key, readiness_branch
execution_status: blocked_on_tooling
evidence_status: none
cases:
  - The cycle key joins the five fields with a bar: expected=the cycle key is those values joined by '|'
  - An equal lastPublishKey skips ensurePublishedForCycle: expected=ensurePublishedForCycle is skipped
  - A different lastPublishKey does not skip ensurePublishedForCycle: expected=ensurePublishedForCycle is not skipped by the key check
  - lastLiveStartKey is recorded before create returns: expected=lastLiveStartKey is recorded before createLiveRaidFromPublished returns
  - An empty warRoomIds list returns before the key is recorded: expected=the call returns before lastLiveStartKey is recorded
  - A minute tick that is not a successful publish does not ensure the readiness board: expected=ensureGvgReadinessBoardIfMissing does not run
  - The readiness board is ensured only inside a successful publish: expected=ensureGvgReadinessBoardIfMissing runs inside that branch
  - A failed auto-start is not retried for the same cycle key: expected=auto-start is not retried
  - A successful auto-start is not repeated for the same cycle key: expected=auto-start is not repeated
<<<
COMMENT: >>>
domain: Raid compose/Party
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-192

[[/SECTION]]

[[SECTION]]
TITLE: Scheduler/RSVP — TST-ROO-176 .. TST-ROO-192 (17 plans)

[REQUIREMENT]
UID: TST-ROO-176
STATUS: Active
TITLE: MaterializeWeekInstances builds week instances from templates and specials, preserves force fields, and rejects bad callers
STATEMENT: >>>
Plan: MaterializeWeekInstances builds week instances from templates and specials, preserves force fields, and rejects bad callers
level: system
verifies: REQ-ROO-114, FNC-ROO-090, API-ROO-060, UNT-ROO-100, CMP-ROO-017
requires_tol: TOL-ROO-006
patterns: ensure_week, force_preserve, idempotent, guild_tz
execution_status: blocked_on_tooling
evidence_status: none
cases:
  - Authenticated materialize writes compositeKey instances: expected=scheduler/instances/{date_eventId} rows are written for that week
  - Force rebuild preserves isCancelled, notes, and title: expected=the rebuilt map keeps those prior isCancelled, notes, and title values
  - Same week without force is idempotent: expected=the week map does not diverge from the prior materialization
  - Guild timezone defaults to Asia/Manila: expected=Monday resolution uses Asia/Manila
  - An unauthenticated caller is rejected: expected=unauthenticated; no instances are materialized
  - An invalid weekMonday is rejected: expected=invalid weekMonday; no instances are materialized
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-114

[REQUIREMENT]
UID: TST-ROO-177
STATUS: Active
TITLE: ReadWeekInstancesAutoEnsure returns the week set and auto-ensures only when the filtered week is empty
STATEMENT: >>>
Plan: ReadWeekInstancesAutoEnsure returns the week set and auto-ensures only when the filtered week is empty
level: system
verifies: REQ-ROO-115, FNC-ROO-091, API-ROO-061, UNT-ROO-101, CMP-ROO-017
requires_tol: TOL-ROO-006
patterns: week_instances, auto_ensure, empty_week
execution_status: blocked_on_tooling
evidence_status: none
cases:
  - Existing week instances are returned: expected=those week instances are returned
  - An empty week triggers auto-ensure before return: expected=MaterializeWeekInstances runs for that Monday, then week instances are returned
  - A non-empty week does not auto-ensure: expected=ensure-week materialization is not called
  - An unauthenticated caller is rejected: expected=unauthenticated; no week instances are returned
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-115

[REQUIREMENT]
UID: TST-ROO-178
STATUS: Active
TITLE: GuildWeekCommitmentsReader returns one guild week with etag, supports 304, and never returns the all-weeks tree
STATEMENT: >>>
Plan: GuildWeekCommitmentsReader returns one guild week with etag, supports 304, and never returns the all-weeks tree
level: system
verifies: REQ-ROO-116, FNC-ROO-092, API-ROO-062, UNT-ROO-102, CMP-ROO-017
requires_tol: TOL-ROO-006
patterns: one_guild_week, etag, 304, not_all_weeks
execution_status: blocked_on_tooling
evidence_status: none
cases:
  - One guild week returns commitments plus etag and weekMonday: expected=commitments whose event date falls in that week only, plus etag and weekMonday
  - An empty week is an empty commitment set: expected=empty commitment set with etag and weekMonday; not an error
  - Matching If-None-Match returns 304 with an empty body: expected=304 with an empty body
  - A non-matching If-None-Match does not 304: expected=the week commitments body is returned (not 304)
  - The all-weeks compositeKey tree is not returned: expected=the response is not the all-weeks RSVP compositeKey tree
  - An unauthenticated caller is rejected: expected=unauthenticated; no commitments body is returned
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-116

[REQUIREMENT]
UID: TST-ROO-179
STATUS: Active
TITLE: ApplyRsvpAvailabilityDecision writes or removes the commitment, debits or refunds leave credits, and rejects guarded inputs
STATEMENT: >>>
Plan: ApplyRsvpAvailabilityDecision writes or removes the commitment, debits or refunds leave credits, and rejects guarded inputs
level: system
verifies: REQ-ROO-117, FNC-ROO-093, API-ROO-063, UNT-ROO-103, CMP-ROO-017
requires_tol: TOL-ROO-006
patterns: rsvp_decision, leave_debit, leave_refund, deadline_guard, none_deletes
execution_status: blocked_on_tooling
evidence_status: none
cases:
  - Confirmed writes displayName, status, and declaredAt: expected=commitment leaf written with displayName, status Confirmed, and declaredAt
  - Leave from non-Leave debits one leave credit: expected=one leave credit is debited against the CMP-014 balance
  - Leave with balance ≤0 fails no_credits: expected=no_credits; commitment is not updated as Leave
  - Leaving Leave for Confirmed or None refunds one credit: expected=one leave credit is refunded
  - status None removes the commitment leaf: expected=the commitment leaf is removed; None is not stored as a status
  - A missing instance is rejected: expected=rejected for missing instance
  - A cancelled instance is rejected: expected=rejected for cancelled instance
  - A past RSVP deadline is rejected: expected=rejected for past deadline
  - A bad status returns 400: expected=400 bad status
  - A missing integer leaveCreditsRemaining is seeded: expected=leaveCreditsRemaining is seeded from the CMP-014 balance leaf
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-117

[REQUIREMENT]
UID: TST-ROO-180
STATUS: Active
TITLE: RsvpStatusVocabulary normalizes statuses and defines calendar-committed and archived predicates
STATEMENT: >>>
Plan: RsvpStatusVocabulary normalizes statuses and defines calendar-committed and archived predicates
level: unit
verifies: REQ-ROO-118, FNC-ROO-094, UNT-ROO-104, CMP-ROO-017
requires_tol: TOL-ROO-006
patterns: canonical_status, normalize, calendar_committed, archived
execution_status: blocked_on_tooling
evidence_status: none
cases:
  - Legacy Confirm normalizes to Confirmed: expected=Confirmed
  - An unknown status normalizes to None: expected=None
  - isCalendarCommitted is true for Confirmed: expected=isCalendarCommitted is true
  - isCalendarCommitted is true for Leave: expected=isCalendarCommitted is true
  - isCalendarCommitted is false for NoConfirm and None: expected=isCalendarCommitted is false
  - isArchivedRsvp includes NoConfirm: expected=isArchivedRsvp is true
  - Exactly four canonical statuses exist: expected=Confirmed, Leave, NoConfirm, and None only
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-118

[REQUIREMENT]
UID: TST-ROO-181
STATUS: Active
TITLE: CloseExpiredRsvpDeadlines marks unanswered raid-roster members NoConfirm only when callable and not skipped
STATEMENT: >>>
Plan: CloseExpiredRsvpDeadlines marks unanswered raid-roster members NoConfirm only when callable and not skipped
level: unit
verifies: REQ-ROO-119, FNC-ROO-095, UNT-ROO-105, CMP-ROO-017
requires_tol: TOL-ROO-006
patterns: close_expired, no_confirm, idempotent_marker, not_on_ticker
execution_status: blocked_on_tooling
evidence_status: none
cases:
  - Past-deadline unanswered raid-roster members become NoConfirm: expected=NoConfirm is written and noConfirmCount is incremented
  - A future deadline is skipped: expected=no NoConfirm writes and no closed marker for that event
  - A start older than 7 days is skipped: expected=no NoConfirm writes and no closed marker for that event
  - An existing deadline_closed marker skips the event: expected=the event is skipped (idempotent)
  - A member already Confirmed, Leave, or NoConfirm is not auto-marked: expected=that member is not rewritten to NoConfirm by this pass
  - The CMP-010 60s clock does not invoke the writer: expected=closeExpiredDeadlines is not scheduled or invoked by that clock
  - A closed marker is stored after marking: expected=attendance/deadline_closed/{eventKey} is stored
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-119

[REQUIREMENT]
UID: TST-ROO-182
STATUS: Active
TITLE: ListSpecialEvents returns the special_events map and {} when empty
STATEMENT: >>>
Plan: ListSpecialEvents returns the special_events map and {} when empty
level: system
verifies: REQ-ROO-120, FNC-ROO-096, API-ROO-064, UNT-ROO-106, CMP-ROO-017
requires_tol: TOL-ROO-006
patterns: special_events_list, empty_object
execution_status: blocked_on_tooling
evidence_status: none
cases:
  - Existing special events are returned: expected=the special_events map/list is returned
  - An empty store returns {}: expected={}
  - An unauthenticated caller is rejected: expected=unauthenticated; no special_events body is returned
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-120

[REQUIREMENT]
UID: TST-ROO-183
STATUS: Active
TITLE: CreateSpecialEvent allocates an officer-created special event with required schedule fields
STATEMENT: >>>
Plan: CreateSpecialEvent allocates an officer-created special event with required schedule fields
level: system
verifies: REQ-ROO-120, FNC-ROO-097, API-ROO-065, UNT-ROO-107, CMP-ROO-017
requires_tol: TOL-ROO-006
patterns: special_event_create, officer, defaults
execution_status: blocked_on_tooling
evidence_status: none
cases:
  - Officer create persists with type default Raid: expected=a new scheduler/special_events/{id} is persisted with type Raid, createdBy, and createdAt
  - isAttendanceTracked and allDay are coerced to boolean: expected=those fields are stored as booleans
  - Missing required schedule fields return 400: expected=400 missing fields
  - A non-officer is rejected with 403: expected=403
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-120

[REQUIREMENT]
UID: TST-ROO-184
STATUS: Active
TITLE: UpdateSpecialEvent updates schedule fields, stamps audit, preserves id, and 404s a missing id
STATEMENT: >>>
Plan: UpdateSpecialEvent updates schedule fields, stamps audit, preserves id, and 404s a missing id
level: system
verifies: REQ-ROO-120, FNC-ROO-098, API-ROO-066, UNT-ROO-108, CMP-ROO-017
requires_tol: TOL-ROO-006
patterns: special_event_update, id_immutable, 404
execution_status: blocked_on_tooling
evidence_status: none
cases:
  - Officer update stamps updatedBy and updatedAt and preserves id: expected=updated fields written; updatedBy and updatedAt set; id unchanged
  - A missing id returns 404: expected=404
  - Missing required schedule fields return 400: expected=400 missing fields
  - A non-officer is rejected with 403: expected=403
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-120

[REQUIREMENT]
UID: TST-ROO-185
STATUS: Active
TITLE: DeleteSpecialEventAndCommitments removes the event and purges only _{eventId} commitment keys
STATEMENT: >>>
Plan: DeleteSpecialEventAndCommitments removes the event and purges only _{eventId} commitment keys
level: system
verifies: REQ-ROO-120, FNC-ROO-099, API-ROO-067, UNT-ROO-109, CMP-ROO-017
requires_tol: TOL-ROO-006
patterns: special_event_delete, commitment_purge, suffix_only
execution_status: blocked_on_tooling
evidence_status: none
cases:
  - Officer delete removes the special event: expected=scheduler/special_events/{id} is removed
  - Commitment keys ending with _{eventId} are purged: expected=those commitment leaves are multi-path nulled
  - Commitment keys not ending with _{eventId} are not purged: expected=those commitments remain
  - A non-officer is rejected with 403: expected=403
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-120

[REQUIREMENT]
UID: TST-ROO-186
STATUS: Active
TITLE: AnnounceWeekAttendanceCard posts via enqueue when officer, channel, and bot readiness pass
STATEMENT: >>>
Plan: AnnounceWeekAttendanceCard posts via enqueue when officer, channel, and bot readiness pass
level: system
verifies: REQ-ROO-121, FNC-ROO-100, API-ROO-068, UNT-ROO-110, CMP-VAL-011
requires_tol: TOL-ROO-006
patterns: announce_week, war_announce, bot_ready, enqueue
execution_status: blocked_on_tooling
evidence_status: none
cases:
  - Officer with mapped channel and ready bot posts via enqueue: expected=Discord enqueue helper posts the weekly attendance card and a card send result is returned
  - An unmapped war-announce channel returns 400: expected=400 unmapped channel
  - Bot offline or circuit open returns 503: expected=503
  - A non-officer is rejected with 403: expected=403
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-121

[REQUIREMENT]
UID: TST-ROO-187
STATUS: Active
TITLE: SchedulerSpaCalendar renders only at /attendance/scheduler and stays a dedicated UI CMP
STATEMENT: >>>
Plan: SchedulerSpaCalendar renders only at /attendance/scheduler and stays a dedicated UI CMP
level: unit
verifies: REQ-ROO-122, FNC-ROO-101, UNT-ROO-111, CMP-ROO-018
requires_tol: TOL-ROO-006
patterns: scheduler_route, dedicated_spa
execution_status: blocked_on_tooling
evidence_status: none
cases:
  - Path /attendance/scheduler renders Scheduler with a signed-in user: expected=Scheduler calendar is rendered
  - A path other than /attendance/scheduler does not render this surface: expected=this Scheduler calendar surface is not rendered
  - The surface is not folded into CMP-004 or CMP-016: expected=it remains the dedicated CMP-018 UI and is not folded into CMP-004 shell or CMP-016 roster SPA
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-122

[REQUIREMENT]
UID: TST-ROO-188
STATUS: Active
TITLE: GvgReadinessCardStaysOnCycleWar keeps the cycle war after deadline and does not fall through when missing
STATEMENT: >>>
Plan: GvgReadinessCardStaysOnCycleWar keeps the cycle war after deadline and does not fall through when missing
level: unit
verifies: REQ-ROO-176, FNC-ROO-177, UNT-ROO-187, CMP-VAL-011
requires_tol: TOL-ROO-006
patterns: gvg_readiness, cycle_war, locked_after_deadline, no_fallthrough
execution_status: blocked_on_tooling
evidence_status: none
cases:
  - A cycle targets the war only when setup fields pass: expected=the cycle targets that war
  - The instance is for the war date's week, not blindly the current week: expected=the scheduler instance is loaded or materialized for the week of that war date
  - After the RSVP deadline the war is kept and confirm/leave are locked: expected=card target stays that war; confirm/leave buttons are locked
  - A missing or cancelled instance does not fall through: expected=card target is missing; it does not fall through to anchored published composition or next open RSVP
  - Otherwise prefer anchored published composition, else next open RSVP: expected=card prefers the anchored published composition, else the next open RSVP
  - Board fingerprint includes the stated fields: expected=fingerprint includes event key, date, timeStart, title, locked-vs-open, and each member RSVP status
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-176

[REQUIREMENT]
UID: TST-ROO-189
STATUS: Active
TITLE: RematerializeDeletesStaleNonSpecial removes absent non-special rows and leaves special rows in place
STATEMENT: >>>
Plan: RematerializeDeletesStaleNonSpecial removes absent non-special rows and leaves special rows in place
level: unit
verifies: REQ-ROO-177, FNC-ROO-178, UNT-ROO-188, CMP-ROO-017
requires_tol: TOL-ROO-006
patterns: rematerialize_sweep, stale_non_special, keep_special
execution_status: blocked_on_tooling
evidence_status: none
cases:
  - A non-special key absent from the generated map is removed: expected=that instance row is removed
  - An isSpecial true row is not deleted: expected=the row stays in place
  - A source 'special' row is not deleted: expected=the row stays in place
  - A key still in the generated map is not removed: expected=that instance is not removed by the sweep
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-177

[REQUIREMENT]
UID: TST-ROO-190
STATUS: Active
TITLE: RaidPhase3WhenRaidEnabled selects raid.phases[3] or phases[3] and keeps the stated fallbacks
STATEMENT: >>>
Plan: RaidPhase3WhenRaidEnabled selects raid.phases[3] or phases[3] and keeps the stated fallbacks
level: unit
verifies: REQ-ROO-178, FNC-ROO-179, UNT-ROO-189, CMP-ROO-017
requires_tol: TOL-ROO-006
patterns: phase3_select, raid_enabled, fallbacks
execution_status: blocked_on_tooling
evidence_status: none
cases:
  - isRaidEnabled true selects event.raid.phases[3]: expected=phase-3 times come from event.raid.phases[3]
  - isRaidEnabled false selects event.phases[3]: expected=phase-3 times come from event.phases[3]
  - Scheduler blocks, shading, and RSVP deadline use that phase 3: expected=scheduler weekly blocks, business-hour shading, and the RSVP deadline clock use those times
  - Missing phase-3 business-hours fallback is 20:55-22:15: expected=fallback 20:55-22:15
  - Day-focus time fallback is 21:30-23:00: expected=fallback 21:30-23:00
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-178

[REQUIREMENT]
UID: TST-ROO-191
STATUS: Active
TITLE: SchedulerCommitmentsOpenWeekChange loads on open and week change only, clears ETag, and narrows settings fields
STATEMENT: >>>
Plan: SchedulerCommitmentsOpenWeekChange loads on open and week change only, clears ETag, and narrows settings fields
level: unit
verifies: REQ-ROO-183, FNC-ROO-184, UNT-ROO-194, CMP-ROO-018
requires_tol: TOL-ROO-006
patterns: no_timer_reget, week_change, etag_clear, settings_fields
execution_status: blocked_on_tooling
evidence_status: none
cases:
  - No timer re-GET while Scheduler stays open: expected=GET /api/attendance/commitments is not repeated on a timer
  - Commitments load when the page opens: expected=commitments are fetched
  - Week change clears stored ETag before the fetch: expected=stored ETag is cleared, then commitments are fetched for the new week
  - Settings GET asks only the three fields: expected=fields requested are only events, specialEventCategories, and timezone
  - Commitments request includes weekMonday when known: expected=the commitments request includes that weekMonday
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-183

[REQUIREMENT]
UID: TST-ROO-192
STATUS: Active
TITLE: AttendanceCardRsvpAnnounceCooldown posts at most one GEN line per minute after a real status change
STATEMENT: >>>
Plan: AttendanceCardRsvpAnnounceCooldown posts at most one GEN line per minute after a real status change
level: unit
verifies: REQ-ROO-189, FNC-ROO-190, UNT-ROO-200, CMP-VAL-011
requires_tol: TOL-ROO-006
patterns: card_announce, cooldown_60s, available_unavailable, no_op_skip
execution_status: blocked_on_tooling
evidence_status: none
cases:
  - A Confirmed status change announces Available: expected=one GEN-room Available line for the cycle activeEventTitle and warDate
  - A Leave status change announces Unavailable: expected=one GEN-room Unavailable line for the cycle activeEventTitle and warDate
  - A second change within 60s for the same key does not announce: expected=no additional GEN-room line
  - A no-op press does not announce: expected=no GEN-room announce
  - A failed applyAttendanceDecision does not announce: expected=no GEN-room announce
  - The line uses cycle title and warDate, not the button event key: expected=line uses activeEventTitle and warDate
  - Missing title, name, or unparseable date use the stated fallbacks: expected=fallbacks 'the raid', 'A raider', and em dash respectively; parseable date is Mon DD, YYYY
  - Confirm-yours clause follows DISCORD_WARANNOUNCE_CHANNEL_ID: expected=when set the line ends with ' Confirm yours at <#id>.'; otherwise that clause is omitted
<<<
COMMENT: >>>
domain: Scheduler/RSVP
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-189

[[/SECTION]]

[[SECTION]]
TITLE: Billing/Capacity — TST-VAL-193 .. TST-VAL-205 (13 plans)

[REQUIREMENT]
UID: TST-VAL-193
STATUS: Active
TITLE: SeatAccessPredicate grants access only for active or future past_due grace, and occupying a slot uses that same predicate
STATEMENT: >>>
Plan: SeatAccessPredicate grants access only for active or future past_due grace, and occupying a slot uses that same predicate
level: unit
verifies: REQ-VAL-049, FNC-VAL-024, UNT-VAL-036, CMP-VAL-009
requires_tol: TOL-ROO-006
patterns: tenant_has_access, past_due_grace, occupying_slot
execution_status: blocked_on_tooling
evidence_status: none
cases:
  - subscription_status active has access: expected=tenantHasAccess is true
  - past_due with grace_until after now has access: expected=tenantHasAccess is true
  - expired past_due grace does not count as access: expected=tenantHasAccess is false
  - past_due without grace_until does not have access: expected=tenantHasAccess is false
  - inactive does not have access: expected=tenantHasAccess is false
  - canceled does not have access: expected=tenantHasAccess is false
  - a missing tenant does not have access: expected=tenantHasAccess is false
  - occupying a slot uses the same predicate as tenantHasAccess: expected=only the accepted tenant occupies a slot; the rejected tenant does not
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-049

[REQUIREMENT]
UID: TST-VAL-194
STATUS: Active
TITLE: PlatformCapacityOccupancy returns activeCount, cap, and full from a public capacity read
STATEMENT: >>>
Plan: PlatformCapacityOccupancy returns activeCount, cap, and full from a public capacity read
level: system
verifies: REQ-VAL-052, FNC-VAL-027, API-VAL-018, UNT-VAL-037, CMP-VAL-009
requires_tol: TOL-ROO-006
patterns: capacity_public, cap_default_20, full_when_gte
execution_status: blocked_on_tooling
evidence_status: none
cases:
  - activeCount counts only SeatAccessPredicate tenants: expected=activeCount equals the number that satisfy the predicate; the others do not count
  - a positive finite BILLING_MAX_ACTIVE_GUILDS is the cap: expected=cap is that number
  - an unset or invalid cap defaults to 20: expected=cap is 20
  - full is true when activeCount is at least cap: expected=full is true
  - full is false when activeCount is below cap: expected=full is false
  - GET /api/billing/capacity does not require login: expected=the response is {activeCount, cap, full}
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-052

[REQUIREMENT]
UID: TST-VAL-195
STATUS: Active
TITLE: BillingStatusPublicView returns the public billing view and refreshes Stripe only when source is stripe
STATEMENT: >>>
Plan: BillingStatusPublicView returns the public billing view and refreshes Stripe only when source is stripe
level: system
verifies: REQ-VAL-053, FNC-VAL-028, API-VAL-019, UNT-VAL-038, CMP-VAL-009
requires_tol: TOL-ROO-006
patterns: billing_status, stripe_refresh, permanent_guard
execution_status: blocked_on_tooling
evidence_status: none
cases:
  - a caller who is not logged in is unauthenticated: expected=unauthenticated; no public billing status view
  - stripe source refreshes tenant state before the view: expected=tenant state is refreshed from the Stripe subscription/customer before the view is built
  - a non-stripe source does not refresh from Stripe: expected=no Stripe refresh
  - the public view returns the stated fields: expected=the view includes allowed, tenantStatus, source, graceUntil, currentPeriodEnd, cancelAtPeriodEnd, stripeCustomer, stripeConfigured, activeCount, and cap for that tenant
  - a permanent source is not overwritten by Stripe refresh: expected=Stripe refresh does not overwrite that billing_source or the seat fields
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-053

[REQUIREMENT]
UID: TST-VAL-196
STATUS: Active
TITLE: StripeCheckoutSession creates a subscription Checkout only when the officer tenant has no seat and capacity remains
STATEMENT: >>>
Plan: StripeCheckoutSession creates a subscription Checkout only when the officer tenant has no seat and capacity remains
level: system
verifies: REQ-VAL-054, FNC-VAL-029, API-VAL-020, UNT-VAL-039, CMP-VAL-009
requires_tol: TOL-ROO-006
patterns: checkout_session, already_has_seat, capacity_reached
execution_status: blocked_on_tooling
evidence_status: none
cases:
  - a caller who is not an authenticated officer, or who has no current tenant, does not get Checkout: expected=no Checkout session is created
  - a tenant that already has access is rejected: expected=400 already has active seat; no Checkout session
  - a full platform does not open Checkout: expected=409 capacity_reached; no Checkout session
  - missing Stripe secret or price id does not open Checkout: expected=503; no Checkout session
  - an eligible officer tenant receives a subscription Checkout URL: expected=a Checkout session in mode=subscription with tenant metadata, and its URL
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-054

[REQUIREMENT]
UID: TST-VAL-197
STATUS: Active
TITLE: StripeCustomerPortal returns a portal URL only for a stripe-sourced tenant that has a customer id
STATEMENT: >>>
Plan: StripeCustomerPortal returns a portal URL only for a stripe-sourced tenant that has a customer id
level: system
verifies: REQ-VAL-055, FNC-VAL-030, API-VAL-021, UNT-VAL-040, CMP-VAL-009
requires_tol: TOL-ROO-006
patterns: customer_portal, stripe_source, return_billing
execution_status: blocked_on_tooling
evidence_status: none
cases:
  - a caller who is not an authenticated officer, or who has no current tenant, does not get a portal: expected=no portal URL is created
  - invite or grandfathered source cannot open the portal: expected=400; no portal URL
  - a stripe source with no customer id cannot open the portal: expected=400; no portal URL
  - a missing Stripe secret does not open the portal: expected=503; no portal URL
  - an eligible stripe customer receives a portal URL back to billing: expected=a portal URL whose return is /workspace/billing
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-055

[REQUIREMENT]
UID: TST-VAL-198
STATUS: Active
TITLE: InviteCodeRedemption activates an invite seat once under the billing lock and returns a re-signed user
STATEMENT: >>>
Plan: InviteCodeRedemption activates an invite seat once under the billing lock and returns a re-signed user
level: system
verifies: REQ-VAL-056, FNC-VAL-031, API-VAL-022, UNT-VAL-041, CMP-VAL-009
requires_tol: TOL-ROO-006
patterns: redeem_invite, billing_lock, one_time_code
execution_status: blocked_on_tooling
evidence_status: none
cases:
  - a caller who is not an authenticated officer, or who has no current tenant, does not redeem: expected=no seat is activated and the invite is not marked redeemed
  - a tenant that already has access is rejected inside the lock: expected=rejected while the billing lock is held; seat is not changed
  - a full platform rejects redemption inside the lock: expected=rejected while the billing lock is held; seat is not activated
  - an unknown code is rejected: expected=rejected; seat is not activated
  - a used code is not redeemed again: expected=rejected; the invite is not redeemed a second time
  - an empty code is rejected: expected=rejected; seat is not activated
  - success stores the invite seat on the tenant: expected=subscription_status=active and billing_source=invite are stored on the tenant
  - success stores the invite redemption: expected=the invite row stores redeemed_tenant_id and redeemed_at
  - success returns a re-signed session user: expected=the response is a re-signed session user
  - redemption does not require Stripe keys: expected=the invite seat still activates; this path does not require Stripe
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-056

[REQUIREMENT]
UID: TST-VAL-199
STATUS: Active
TITLE: StripeWebhookLifecycle verifies the raw body and dispatches only the listed billing events
STATEMENT: >>>
Plan: StripeWebhookLifecycle verifies the raw body and dispatches only the listed billing events
level: system
verifies: REQ-VAL-057, FNC-VAL-032, API-VAL-023, UNT-VAL-042, CMP-VAL-009
requires_tol: TOL-ROO-006
patterns: webhook_raw_body, stripe_signature, listed_events
execution_status: blocked_on_tooling
evidence_status: none
cases:
  - the signature is checked on the raw body before JSON parsing: expected=the signature is verified against the raw body; JSON parsing does not run first
  - missing webhook secret or client is rejected: expected=503
  - a bad signature is rejected: expected=400 bad signature
  - each listed event type is dispatched: expected=that event is dispatched as a lifecycle update
  - an unlisted event type does not drive a lifecycle update: expected=no lifecycle update from this unit
  - a handled delivery returns received: expected={received: true}
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-057

[REQUIREMENT]
UID: TST-VAL-200
STATUS: Active
TITLE: OverflowCancelRefund rejects checkout activation for a missing tenant, a permanent source, or a full platform, and does not reject an already-active stripe seat
STATEMENT: >>>
Plan: OverflowCancelRefund rejects checkout activation for a missing tenant, a permanent source, or a full platform, and does not reject an already-active stripe seat
level: unit
verifies: REQ-VAL-058, FNC-VAL-033, UNT-VAL-043, CMP-VAL-009
requires_tol: TOL-ROO-006
patterns: overflow_reject, cancel_refund, already_active
execution_status: blocked_on_tooling
evidence_status: none
cases:
  - a missing tenant is not activated: expected=reject; do not activate a seat; cancel that subscription id; refund via payment_intent or charge
  - a permanent source is not activated: expected=reject; do not activate; cancel that subscription id; refund via payment_intent or charge
  - capacity already full is not activated: expected=reject; do not activate; cancel that subscription id; refund via payment_intent or charge
  - an already-active stripe seat for the same tenant is not an overflow reject: expected=this unit does not treat that seat as an overflow reject and does not cancel or refund it
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-058

[REQUIREMENT]
UID: TST-VAL-201
STATUS: Active
TITLE: PastDueGrace sets past_due and a grace window, skips permanent sources, and does not reset an open grace
STATEMENT: >>>
Plan: PastDueGrace sets past_due and a grace window, skips permanent sources, and does not reset an open grace
level: unit
verifies: REQ-VAL-059, FNC-VAL-034, UNT-VAL-044, CMP-VAL-009
requires_tol: TOL-ROO-006
patterns: past_due, grace_days, open_grace
execution_status: blocked_on_tooling
evidence_status: none
cases:
  - a permanent source does not enter past_due on this path: expected=subscription_status and grace_until are left unchanged
  - an open future grace window is not reset: expected=subscription_status and grace_until are left unchanged
  - otherwise status becomes past_due and grace_until is now plus the configured days: expected=subscription_status=past_due and grace_until=now plus BILLING_PAST_DUE_GRACE_DAYS
  - unset grace days default to 3: expected=grace_until=now plus 3 days and subscription_status=past_due
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-059

[REQUIREMENT]
UID: TST-VAL-202
STATUS: Active
TITLE: PermanentBillingSources keeps invite and grandfathered seats from being overwritten by Stripe
STATEMENT: >>>
Plan: PermanentBillingSources keeps invite and grandfathered seats from being overwritten by Stripe
level: unit
verifies: REQ-VAL-060, FNC-VAL-035, UNT-VAL-045, CMP-VAL-009
requires_tol: TOL-ROO-006
patterns: permanent_source, invite, grandfathered
execution_status: blocked_on_tooling
evidence_status: none
cases:
  - invite is permanent and is not overwritten: expected=billing_source and seat fields are not overwritten; the attempt is skipped or rejected
  - grandfathered is permanent and is not overwritten: expected=billing_source and seat fields are not overwritten; the attempt is skipped or rejected
  - a source that is neither invite nor grandfathered is not permanent: expected=the permanence guard allows the apply
  - status refresh from Stripe runs only for billing_source stripe: expected=the Stripe status refresh applies
  - status refresh from Stripe does not run for a non-stripe source: expected=the Stripe status refresh does not apply
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-060

[REQUIREMENT]
UID: TST-VAL-203
STATUS: Active
TITLE: StripeOptionalBoot continues boot, invite redemption, and capacity without Stripe keys, and fails Stripe call sites closed
STATEMENT: >>>
Plan: StripeOptionalBoot continues boot, invite redemption, and capacity without Stripe keys, and fails Stripe call sites closed
level: unit
verifies: REQ-VAL-061, FNC-VAL-036, UNT-VAL-046, CMP-VAL-009
requires_tol: TOL-ROO-006
patterns: stripe_optional_boot, invite_without_stripe, call_site_503
execution_status: blocked_on_tooling
evidence_status: none
cases:
  - missing Stripe env does not fail boot: expected=boot does not fail solely because those keys are absent
  - invite redemption does not call Stripe: expected=redemption succeeds and the invite path does not call Stripe
  - capacity and access evaluation do not need Stripe: expected=the evaluation succeeds without a Stripe API call
  - Checkout, portal, and webhook fail closed when unconfigured: expected=503
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-061

[REQUIREMENT]
UID: TST-VAL-204
STATUS: Active
TITLE: SpaBillingRedirect sends a disallowed subscription to /workspace/billing except the stated paths, and also redirects HTTP 402
STATEMENT: >>>
Plan: SpaBillingRedirect sends a disallowed subscription to /workspace/billing except the stated paths, and also redirects HTTP 402
level: unit
verifies: REQ-VAL-051, FNC-VAL-026, UNT-VAL-047, CMP-VAL-004
requires_tol: TOL-ROO-006
patterns: spa_redirect, exempt_paths, http_402
execution_status: blocked_on_tooling
evidence_status: none
cases:
  - subscriptionAllowed false on a non-exempt path redirects to billing: expected=navigate to /workspace/billing
  - the exempt paths are not forced off: expected=no billing redirect
  - an apiFetch HTTP 402 redirects to billing: expected=the browser redirects to /workspace/billing
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-051

[REQUIREMENT]
UID: TST-VAL-205
STATUS: Active
TITLE: RequireActiveSubscriptionGate returns 409 when there is no tenant and 402 payment_required when the seat is inactive
STATEMENT: >>>
Plan: RequireActiveSubscriptionGate returns 409 when there is no tenant and 402 payment_required when the seat is inactive
level: unit
verifies: REQ-VAL-050, FNC-VAL-025, UNT-VAL-034, CMP-VAL-008
requires_tol: TOL-ROO-006
patterns: payment_required, tenant_required, seat_gate
execution_status: blocked_on_tooling
evidence_status: none
cases:
  - no current tenant is 409 tenant_required: expected=409 tenant_required; the handler does not continue
  - an inactive seat is 402 payment_required: expected=402 {code: payment_required} with the seat-needed message; this gate does not recompute grace
  - an active seat continues: expected=the handler continues; the gate does not deny
<<<
COMMENT: >>>
domain: Billing/Capacity
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-050

[[/SECTION]]

[[SECTION]]
TITLE: Data isolation/Storage — TST-VAL-206 .. TST-VAL-214 (9 plans)

[REQUIREMENT]
UID: TST-VAL-206
STATUS: Active
TITLE: BindRequestHandlersRunWithTenant scopes a resolved tenant with runWithTenant, stamps tenant_id, and returns 409 on a bound route with no tenant
STATEMENT: >>>
Plan: BindRequestHandlersRunWithTenant scopes a resolved tenant with runWithTenant, stamps tenant_id, and returns 409 on a bound route with no tenant
level: unit
verifies: REQ-VAL-158, FNC-VAL-159, UNT-VAL-169, CMP-VAL-008
requires_tol: TOL-ROO-006
patterns: run_with_tenant, tenant_resolve_order, tenant_required
execution_status: blocked_on_tooling
evidence_status: none
cases:
  - session currentTenantId is preferred: expected=attached tenant is S
  - signed profile is used when there is no session tenant: expected=attached tenant is P; the header is not used
  - x-tenant-id is used only when no session tenant and no signed profile: expected=attached tenant is H
  - a present tenant loads the request-scoped settings cache: expected=that tenant's settings are loaded into the request-scoped cache
  - the rest of the handler runs inside runWithTenant: expected=the remainder of the handler chain runs inside runWithTenant(T)
  - an operational row is stamped with the bound tenant_id: expected=the stored row is keyed and stamped with tenant_id T
  - a store write with no tenant in context is refused: expected=the write is refused
  - a public path with no tenant proceeds: expected=the path proceeds without a tenant; it is not 409 tenant_required
  - a bound route with no tenant is 409 tenant_required: expected=409 tenant_required
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-158

[REQUIREMENT]
UID: TST-VAL-207
STATUS: Active
TITLE: RejectSilentXTenantIdSwitch keeps the session tenant when x-tenant-id disagrees, and lets the header seed only when no session tenant exists
STATEMENT: >>>
Plan: RejectSilentXTenantIdSwitch keeps the session tenant when x-tenant-id disagrees, and lets the header seed only when no session tenant exists
level: unit
verifies: REQ-VAL-159, FNC-VAL-160, UNT-VAL-170, CMP-VAL-008
requires_tol: TOL-ROO-006
patterns: x_tenant_id, no_silent_switch, header_seed
execution_status: blocked_on_tooling
evidence_status: none
cases:
  - a mismatched x-tenant-id does not replace the session tenant: expected=effective tenant id is session.currentTenantId; the header is not adopted
  - the header seeds a tenant only when no session tenant is established: expected=effective tenant id is the header value
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-159

[REQUIREMENT]
UID: TST-VAL-208
STATUS: Active
TITLE: MultiTenantRelationalSchema defines the named tables, puts tenant_id on tenant-scoped keys, and keys platform_state and tenants differently
STATEMENT: >>>
Plan: MultiTenantRelationalSchema defines the named tables, puts tenant_id on tenant-scoped keys, and keys platform_state and tenants differently
level: unit
verifies: REQ-VAL-160, FNC-VAL-161, UNT-VAL-171, CMP-VAL-027
requires_tol: TOL-ROO-006
patterns: relational_schema, tenant_id_pk, platform_state_key
execution_status: blocked_on_tooling
evidence_status: none
cases:
  - migrate applies the named tables: expected=applied schema includes tables tenants, invite_codes, tenant_settings, members, auction_requests, past_auction_awards, loot_history, attendance_commitments, schedule_instances, special_events, json_docs, platform_state
  - a tenant-scoped operational table keys tenant_id: expected=tenant_id, a foreign key to tenants, is in the primary key or is the primary key
  - platform_state is keyed by key only: expected=keyed by key only; tenant_id is not part of the key
  - tenants.id is the Discord guild id: expected=tenants.id is the Discord guild id primary key
  - schema ownership is applied by migrate on boot: expected=this schema is applied via migrate; schema ownership is this unit
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-160

[REQUIREMENT]
UID: TST-VAL-209
STATUS: Active
TITLE: TenantPathStoreJsonDocsCollections routes mapped paths to dedicated tables, other trees to json_docs, and refuses an unbound write
STATEMENT: >>>
Plan: TenantPathStoreJsonDocsCollections routes mapped paths to dedicated tables, other trees to json_docs, and refuses an unbound write
level: unit
verifies: REQ-VAL-161, FNC-VAL-162, UNT-VAL-172, CMP-VAL-027
requires_tol: TOL-ROO-006
patterns: tenant_store, json_docs, dedicated_collection, unbound_write
execution_status: blocked_on_tooling
evidence_status: none
cases:
  - getTenantStore binds the ALS tenant: expected=the store handle is bound to T
  - getTenantStoreFor binds the explicit tenant: expected=the store handle is bound to E
  - mapped collection paths use dedicated tables, not json_docs: expected=each path uses a dedicated table; none of these paths is stored as json_docs
  - a dedicated collection row stores tenant_id: expected=the dedicated-table row is stamped with tenant_id T
  - attendance/commitments maps to attendance_commitments: expected=stored in attendance_commitments
  - settings/configuration maps to tenant_settings.configuration: expected=stored in tenant_settings.configuration
  - any other nested tree uses json_docs rooted at the first two segments: expected=stored in json_docs; document root is the first two path segments compositions/board
  - the store exposes the Firebase-style adapter operations: expected=once, set, update, remove, transaction, push, and child are available; this is an adapter over relational storage, not a Firebase runtime
  - a write with no tenant in context is refused: expected=the write is refused
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-161

[REQUIREMENT]
UID: TST-VAL-210
STATUS: Active
TITLE: PlatformWideStateViaPlatformState maps discord_circuit onto platform_state and does not stamp tenant_id
STATEMENT: >>>
Plan: PlatformWideStateViaPlatformState maps discord_circuit onto platform_state and does not stamp tenant_id
level: unit
verifies: REQ-VAL-162, FNC-VAL-163, UNT-VAL-173, CMP-VAL-027
requires_tol: TOL-ROO-006
patterns: platform_state, discord_circuit, no_tenant_stamp
execution_status: blocked_on_tooling
evidence_status: none
cases:
  - scheduler/discord_circuit maps to key discord_circuit: expected=platform_state key is discord_circuit
  - platform_state access does not require a tenant: expected=the read or write proceeds; a tenant context is not required
  - the stored platform_state row has no tenant_id: expected=the stored row is not stamped with tenant_id
  - another platform key uses platform_state, not a per-guild table: expected=stored in the same platform_state table; not under a per-guild table and not under tenant json_docs
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-162

[REQUIREMENT]
UID: TST-VAL-211
STATUS: Active
TITLE: SharedDomainPackageParity exports attendance, composition, raid-cycle, and in-game alias helpers from one package
STATEMENT: >>>
Plan: SharedDomainPackageParity exports attendance, composition, raid-cycle, and in-game alias helpers from one package
level: unit
verifies: REQ-VAL-163, FNC-VAL-164, UNT-VAL-174, CMP-VAL-028
requires_tol: TOL-ROO-006
patterns: shared_package, attendance_status, fe_be_parity
execution_status: blocked_on_tooling
evidence_status: none
cases:
  - attendance status constants and normalizers are exported: expected=Confirmed, Leave, NoConfirm, and None are exported, plus normalizers
  - composition tab helpers include a cross-tab uniqueness check: expected=the helpers are exported and include a cross-tab uniqueness check
  - raid cycle helpers are exported: expected=raid cycle helpers are exported from the shared package
  - in-game alias helpers are exported: expected=in-game alias helpers are exported from the shared package
  - the API process and the SPA use the same entry points: expected=both consume the same shared-package entry points
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-163

[REQUIREMENT]
UID: TST-VAL-212
STATUS: Active
TITLE: TenantABIsolationVerificationScript passes only when B cannot read A's members or web_requests, and skips when DATABASE_URL is unset
STATEMENT: >>>
Plan: TenantABIsolationVerificationScript passes only when B cannot read A's members or web_requests, and skips when DATABASE_URL is unset
level: unit
verifies: REQ-VAL-164, FNC-VAL-165, UNT-VAL-175, CMP-VAL-027
requires_tol: TOL-ROO-006
patterns: test_isolation, isolation_failed, database_url_skip
execution_status: blocked_on_tooling
evidence_status: none
cases:
  - the check is npm run test:isolation: expected=the script runs as npm run test:isolation
  - an unset DATABASE_URL skips cleanly: expected=the script skips cleanly; it does not report PASS and it does not throw ISOLATION FAILED
  - B cannot see A's members or web_requests: expected=script result PASS
  - a leak is ISOLATION FAILED and non-zero: expected=throws ISOLATION FAILED and exits non-zero
  - both tenants are removed after the check: expected=both tenants are cleaned up
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-164

[REQUIREMENT]
UID: TST-VAL-213
STATUS: Active
TITLE: DefaultWorkspaceTimezoneWallClock seeds Asia/Manila and formats guild wall time with Intl formatToParts
STATEMENT: >>>
Plan: DefaultWorkspaceTimezoneWallClock seeds Asia/Manila and formats guild wall time with Intl formatToParts
level: unit
verifies: REQ-VAL-165, FNC-VAL-166, UNT-VAL-176, CMP-VAL-005
requires_tol: TOL-ROO-006
patterns: asia_manila, format_to_parts, workspace_defaults
execution_status: blocked_on_tooling
evidence_status: none
cases:
  - workspace defaults store Asia/Manila and empty display fields: expected=timezone is Asia/Manila; guildDisplayName is empty; guildLogoUrl is empty; adminRoles is []
  - an omitted timezone defaults to Asia/Manila: expected=the helper uses Asia/Manila
  - a provided timezone is the one the helper uses: expected=the helper uses T
  - formatting uses Intl formatToParts, not toISOString date keys: expected=uses Intl formatToParts against that timezone; does not use toISOString date keys
  - seeded workspace settings persist the defaults: expected=the defaults are persisted via the CMP-027 store
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-165

[REQUIREMENT]
UID: TST-VAL-214
STATUS: Active
TITLE: DefaultRoConfigurationSeeds merges the named RO defaults, including leave credits 3 and the four special-event categories, with workspace defaults
STATEMENT: >>>
Plan: DefaultRoConfigurationSeeds merges the named RO defaults, including leave credits 3 and the four special-event categories, with workspace defaults
level: unit
verifies: REQ-VAL-166, FNC-VAL-167, UNT-VAL-177, CMP-VAL-007
requires_tol: TOL-ROO-006
patterns: ro_seeds, default_leave_credits, special_event_categories
execution_status: blocked_on_tooling
evidence_status: none
cases:
  - items and events start empty: expected=items is []; events is {}
  - leave credits and live-raid caps are the named numbers: expected=defaultLeaveCredits is 3; liveRaidMaxConfigs is 5; liveRaidMaxWarRooms is 2
  - specialEventCategories is the four named categories: expected=specialEventCategories is ['Raid','Meeting','PVP','Casual']
  - warRooms, jobs, and roles are empty placeholders: expected=warRooms is {}; jobs is {}; roles is {}
  - help embed URLs start empty: expected=helpEmbedUrl is ''; raidHelpEmbedUrl is ''
  - RO seeds merge with workspace defaults: expected=DEFAULT_CONFIGURATION is these RO seeds merged with workspace defaults
<<<
COMMENT: >>>
domain: Data isolation/Storage
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-166

[[/SECTION]]

[[SECTION]]
TITLE: Adventurer Guild — TST-ROO-215 .. TST-ROO-223 (9 plans)

[REQUIREMENT]
UID: TST-ROO-215
STATUS: Active
TITLE: ListAdventurerGuildHighlights returns newest-first highlights for an AG member and refuses everyone else
STATEMENT: >>>
Plan: ListAdventurerGuildHighlights returns newest-first highlights for an AG member and refuses everyone else
level: system
verifies: REQ-ROO-152, FNC-ROO-151, API-ROO-108, UNT-ROO-161, CMP-ROO-025
requires_tol: TOL-ROO-006
patterns: highlights_newest_first, ag_mount_gate, highlight_fields
execution_status: blocked_on_tooling
evidence_status: none
cases:
  - Unauthenticated caller is not given highlights: expected=unauthenticated; highlights[] is not returned
  - Missing tenant fails the AG mount gate: expected=403 mount/game gate; highlights[] is not returned
  - No active seat fails the AG mount gate: expected=403 mount/game gate; highlights[] is not returned
  - requireGame(adventurer-guild) failure is the mount gate: expected=403 mount/game gate; highlights[] is not returned
  - Member list is newest-first by createdAt: expected=highlights[] is ordered newest-first by createdAt, so B then A
  - Each highlight carries the named fields: expected=that highlight includes id, caption, url, mime, ext, kind, objectPath, size, createdBy, createdByName, createdAt
  - Listing highlights is read-only: expected=the highlights map is not written; the output is highlights[]
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-152

[REQUIREMENT]
UID: TST-ROO-216
STATUS: Active
TITLE: UploadHighlightMediaWithCaption stores a magic-byte image or video and a sliced caption, or rejects the upload
STATEMENT: >>>
Plan: UploadHighlightMediaWithCaption stores a magic-byte image or video and a sliced caption, or rejects the upload
level: system
verifies: REQ-ROO-153, FNC-ROO-152, API-ROO-109, UNT-ROO-162, CMP-ROO-025
requires_tol: TOL-ROO-006
patterns: highlight_upload, magic_bytes, caption_280, storage_503
execution_status: blocked_on_tooling
evidence_status: none
cases:
  - A caller who is not an AG mount member is refused: expected=403
  - A missing file is rejected: expected=400 missing file
  - A file over the size limit is rejected with the 25 MB message: expected=400 with a human message that states 25 MB
  - Known magic bytes are image or video: expected=png/jpg/gif/webp are kind image; mp4/webm are kind video; neither is the unknown-type rejection
  - Unknown magic bytes are rejected: expected=400
  - Unconfigured object storage is rejected: expected=503
  - A caption is trimmed and sliced to 280: expected=stored caption is trimmed and sliced to ≤280
  - An omitted caption does not reject the upload: expected=the upload is not rejected for a missing caption
  - The highlights leaf stores the named media fields: expected=adventurer-guild/highlights/{id} is stored with a UUID id, createdBy from the session, createdAt now, public url, mime, ext, kind, objectPath, and size
  - The response is the highlight record: expected=the returned output is that highlight record
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-153

[REQUIREMENT]
UID: TST-ROO-217
STATUS: Active
TITLE: DeleteHighlightCreatorOrOfficer removes the leaf for the creator or an officer, and still removes it when storage delete fails
STATEMENT: >>>
Plan: DeleteHighlightCreatorOrOfficer removes the leaf for the creator or an officer, and still removes it when storage delete fails
level: system
verifies: REQ-ROO-154, FNC-ROO-153, API-ROO-110, UNT-ROO-163, CMP-ROO-025
requires_tol: TOL-ROO-006
patterns: highlight_delete, creator_or_officer, storage_best_effort
execution_status: blocked_on_tooling
evidence_status: none
cases:
  - A missing highlight is 404: expected=404
  - The creator may delete their highlight: expected=adventurer-guild/highlights/{id} is removed; output is deleted
  - An officer may delete a highlight they did not create: expected=adventurer-guild/highlights/{id} is removed; output is deleted
  - A non-creator who is not an officer is refused: expected=403; the highlight leaf is not removed
  - Storage delete is best-effort by objectPath: expected=storage object delete is attempted for that objectPath and is best-effort
  - A failed storage delete does not keep the leaf: expected=adventurer-guild/highlights/{id} is still removed and the output is success (deleted)
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-154

[REQUIREMENT]
UID: TST-ROO-218
STATUS: Active
TITLE: ListAgCalendarEventsNativeAndContributed returns overlapping native rows and enabled-game contributions
STATEMENT: >>>
Plan: ListAgCalendarEventsNativeAndContributed returns overlapping native rows and enabled-game contributions
level: system
verifies: REQ-ROO-155, FNC-ROO-154, API-ROO-111, UNT-ROO-164, CMP-ROO-025
requires_tol: TOL-ROO-006
patterns: ag_calendar_range, native_overlap, allday_vs_timed, contributed_schedules
execution_status: blocked_on_tooling
evidence_status: none
cases:
  - A caller who is not an AG mount member is refused: expected=403
  - A missing from becomes today UTC: expected=from is today as a UTC YYYY-MM-DD date
  - A missing to becomes from: expected=to equals from
  - A native event that overlaps the range is included: expected=that row is in native[]
  - A native event that does not overlap does not count: expected=that row is not in native[]
  - A native allDay event uses date strings: expected=that native row uses date strings, not an ISO start/end conversion
  - A timed native event converts wall-clock through the tenant timezone: expected=start/end are ISO instants converted from the wall-clock via the tenant timezone
  - Other enabled games contribute schedules for the same range: expected=those contributions are in contributed[]
  - A game that is not enabled does not contribute: expected=that game's schedules are not in contributed[]
  - The response separates native, contributed, and combined events: expected=the response has timezone, native[], contributed[], and events[] combined from native and contributed
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-155

[REQUIREMENT]
UID: TST-ROO-219
STATUS: Active
TITLE: CreateNativeAgEvent stores an officer native event, defaults dateEnd, and sets allDay only when body.allDay is true
STATEMENT: >>>
Plan: CreateNativeAgEvent stores an officer native event, defaults dateEnd, and sets allDay only when body.allDay is true
level: system
verifies: REQ-ROO-156, FNC-ROO-155, API-ROO-112, UNT-ROO-165, CMP-ROO-025
requires_tol: TOL-ROO-006
patterns: native_event_create, allday_strict, event_defaults, no_contributed
execution_status: blocked_on_tooling
evidence_status: none
cases:
  - A non-officer is refused: expected=403; no adventurer-guild/events leaf is created
  - An empty title is rejected: expected=400
  - A date that is not YYYY-MM-DD is rejected: expected=400
  - Title is sliced to 120: expected=stored title is sliced to ≤120
  - Description is sliced to 500: expected=stored description is sliced to ≤500
  - Omitted dateEnd defaults to date: expected=stored dateEnd equals date
  - Created times are 18:00 and 19:00: expected=timeStart is 18:00; timeEnd is 19:00
  - allDay is true only when body.allDay is true: expected=stored allDay is true
  - Any other allDay value does not count as true: expected=allDay is not true
  - The native event leaf is stored: expected=adventurer-guild/events/{id} is persisted
  - The calendar projection is separate from the stored record: expected=the response includes the stored record and a calendar event that is native, readOnly false, sourceGameId adventurer-guild
  - Create does not create a contributed schedule: expected=no contributed schedule is created
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-156

[REQUIREMENT]
UID: TST-ROO-220
STATUS: Active
TITLE: UpdateNativeAgEvent merges provided fields onto the native leaf and leaves contributed schedules alone
STATEMENT: >>>
Plan: UpdateNativeAgEvent merges provided fields onto the native leaf and leaves contributed schedules alone
level: system
verifies: REQ-ROO-156, FNC-ROO-156, API-ROO-113, UNT-ROO-166, CMP-ROO-025
requires_tol: TOL-ROO-006
patterns: native_event_update, merge_when_provided, updated_at
execution_status: blocked_on_tooling
evidence_status: none
cases:
  - A non-officer is refused: expected=403; the leaf is unchanged
  - A missing event is 404: expected=404
  - Provided title and description are sliced onto the current leaf: expected=stored title is sliced to ≤120 and stored description is sliced to ≤500, merged over the current leaf
  - Provided date fields replace the current values: expected=those provided values are stored on adventurer-guild/events/{id}
  - Omitted fields do not count as overwrites: expected=date, dateEnd, timeStart, timeEnd, and allDay stay as they were; title is the merged title
  - updatedAt is set: expected=the stored leaf has updatedAt set
  - The native leaf is persisted: expected=adventurer-guild/events/{id} is persisted with the merged fields
  - The response is the calendar event plus the record: expected=the output is the calendar event plus the stored record
  - Update does not mutate contributed schedules: expected=contributed schedules are unchanged
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-156

[REQUIREMENT]
UID: TST-ROO-221
STATUS: Active
TITLE: DeleteNativeAgEvent removes a native event for an officer and still succeeds when the leaf is already absent
STATEMENT: >>>
Plan: DeleteNativeAgEvent removes a native event for an officer and still succeeds when the leaf is already absent
level: system
verifies: REQ-ROO-156, FNC-ROO-157, API-ROO-114, UNT-ROO-167, CMP-ROO-025
requires_tol: TOL-ROO-006
patterns: native_event_delete, idempotent_delete, contributed_untouched
execution_status: blocked_on_tooling
evidence_status: none
cases:
  - A non-officer is refused: expected=403; the native leaf is not removed
  - An existing native event is removed: expected=adventurer-guild/events/{id} is removed; output is deleted
  - An already absent id still succeeds: expected=success (deleted); absence does not fail the delete
  - Contributed schedules do not count as native leaves: expected=contributed schedules are not affected
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-156

[REQUIREMENT]
UID: TST-ROO-222
STATUS: Active
TITLE: AdventurerGuildHallSpaRoutes renders Highlights and Events and Navigate-replaces the highlights alias
STATEMENT: >>>
Plan: AdventurerGuildHallSpaRoutes renders Highlights and Events and Navigate-replaces the highlights alias
level: unit
verifies: REQ-ROO-157, FNC-ROO-158, UNT-ROO-168, CMP-ROO-026
requires_tol: TOL-ROO-006
patterns: hall_routes, highlights_alias, game_path_gate
execution_status: blocked_on_tooling
evidence_status: none
cases:
  - The hall root renders Highlights: expected=Highlights page is rendered
  - The events path renders Guild Events: expected=Guild Events page is rendered
  - The highlights alias Navigate-replaces to the hall root: expected=Navigate-replace to /games/adventurer-guild
  - Game path gating still applies: expected=Highlights and Guild Events are not rendered; the game-path gate redirect applies
  - Hall routes stay on this UI and are not folded into the shell: expected=they are CMP-026 Hall routes and are not folded into CMP-004
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-157

[REQUIREMENT]
UID: TST-ROO-223
STATUS: Active
TITLE: HighlightVideoPreloadAndCache sets gallery preload to metadata and stores cacheControl 31536000
STATEMENT: >>>
Plan: HighlightVideoPreloadAndCache sets gallery preload to metadata and stores cacheControl 31536000
level: unit
verifies: REQ-ROO-196, FNC-ROO-197, UNT-ROO-207, CMP-ROO-025
requires_tol: TOL-ROO-006
patterns: video_preload_metadata, cache_control_31536000, size_cap_25mb
execution_status: blocked_on_tooling
evidence_status: none
cases:
  - A gallery video element preloads metadata: expected=preload is metadata
  - A highlight upload stores cacheControl 31536000: expected=the storage object is stored with cacheControl 31536000
  - A file over 25MB does not count as within the cap: expected=over 25MB; the size cap remains 25MB
<<<
COMMENT: >>>
domain: Adventurer Guild
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-196

[[/SECTION]]

[[SECTION]]
TITLE: Frontend shell/UX — TST-VAL-224 .. TST-VAL-229 (6 plans)

[REQUIREMENT]
UID: TST-VAL-224
STATUS: Active
TITLE: PublicFullBleedLandingRedirect renders unauthenticated landing outside MainLayout and redirects authenticated users, login, and unauth shells
STATEMENT: >>>
Plan: PublicFullBleedLandingRedirect renders unauthenticated landing outside MainLayout and redirects authenticated users, login, and unauth shells
level: unit
verifies: REQ-VAL-167, FNC-VAL-168, UNT-VAL-178, CMP-VAL-004
requires_tol: TOL-ROO-006
patterns: landing_full_bleed, post_login_navigate, login_query_preserve, unauth_shell_to_landing
execution_status: blocked_on_tooling
evidence_status: none
cases:
  - Unauthenticated landing renders full-bleed outside MainLayout: expected=landing renders outside MainLayout (full-bleed, no left nav and no toolbar)
  - Session sync loading does not block landing: expected=`/landing` stays reachable; session sync loading does not block it
  - An authenticated user on landing navigates to the post-login path: expected=Navigate to resolvePostLoginPath(user), in the order select-guild, then billing, then choose-game, then incomplete setup, then first enabled game home
  - Login redirects to landing and preserves the query string: expected=redirect to `/landing` with that query string preserved
  - Unauthenticated root and shells redirect to landing: expected=redirect to `/landing`
<<<
COMMENT: >>>
domain: Frontend shell/UX
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-167

[REQUIREMENT]
UID: TST-VAL-225
STATUS: Active
TITLE: MainLayoutManifestLeftNav composes MainLayout chrome and takes LeftNavBar modules from the active game manifest
STATEMENT: >>>
Plan: MainLayoutManifestLeftNav composes MainLayout chrome and takes LeftNavBar modules from the active game manifest
level: unit
verifies: REQ-VAL-168, FNC-VAL-169, UNT-VAL-179, CMP-VAL-004
requires_tol: TOL-ROO-006
patterns: mainlayout_chrome, manifest_modules, standalone_outside
execution_status: blocked_on_tooling
evidence_status: none
cases:
  - MainLayout composes top chrome, LeftNavBar, and scrollable content: expected=top chrome (brand/game switcher + toolbar), LeftNavBar, and scrollable main content
  - Ragnarok Origin modules are Auction and Raid with the named items: expected=LeftNavBar modules are Auction (Request, Mimic Book, Request History, Past Auction) and Raid (MasterList, Profile, Peak Hours, Raid Config, War Room, GVG Attendance, GVG History, Attendance, Calendar)
  - Adventurer Guild modules are Hall: expected=LeftNavBar module is Hall (Highlights, Events)
  - Labels and paths come from the manifest modules: expected=LeftNavBar labels and paths are taken from those manifest modules, not hard-coded per page
  - Standalone flows stay outside MainLayout: expected=those flows stay outside MainLayout
  - Workspace settings is inside MainLayout: expected=rendered inside MainLayout
<<<
COMMENT: >>>
domain: Frontend shell/UX
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-168

[REQUIREMENT]
UID: TST-VAL-226
STATUS: Active
TITLE: HelpGuideModal lists helpKey guides, loads auction and raid embed URLs, and does not iframe on mobile
STATEMENT: >>>
Plan: HelpGuideModal lists helpKey guides, loads auction and raid embed URLs, and does not iframe on mobile
level: unit
verifies: REQ-VAL-169, FNC-VAL-170, UNT-VAL-180, CMP-VAL-004
requires_tol: TOL-ROO-006
patterns: helpkey_entry, help_embed_urls, desktop_iframe_mobile_tab
execution_status: blocked_on_tooling
evidence_status: none
cases:
  - Help Guide entry is available when a module has a helpKey: expected=Help Guide entry is available
  - Auction and raid guide URLs load from settings/help: expected=the auction guide URL is helpEmbedUrl and the raid guide URL is raidHelpEmbedUrl
  - An empty help URL does not count as configured: expected=not-configured state for that empty URL
  - Desktop embeds the selected guide in an iframe: expected=the selected guide URL is embedded in an iframe inside the modal
  - Mobile does not iframe and opens an external tab: expected=no iframe; an external link opens the URL in a new tab (target=_blank)
  - The modal lists guides, drills into the selected guide, and close returns to the shell: expected=the modal lists the guides, then drills into the selected guide; close returns to the shell
<<<
COMMENT: >>>
domain: Frontend shell/UX
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-169

[REQUIREMENT]
UID: TST-VAL-227
STATUS: Active
TITLE: WorkspaceChooseGameBillingRoSetupRoutes mounts the four shells and applies unauth and subscription gates
STATEMENT: >>>
Plan: WorkspaceChooseGameBillingRoSetupRoutes mounts the four shells and applies unauth and subscription gates
level: unit
verifies: REQ-VAL-170, FNC-VAL-171, UNT-VAL-181, CMP-VAL-004
requires_tol: TOL-ROO-006
patterns: workspace_routes, unauth_to_landing, subscription_billing_force
execution_status: blocked_on_tooling
evidence_status: none
cases:
  - Workspace settings mounts inside MainLayout for an authenticated tenant: expected=Workspace Settings rendered inside MainLayout
  - Choose Game mounts standalone outside MainLayout: expected=Choose Game rendered standalone, outside MainLayout
  - Billing mounts standalone outside MainLayout: expected=Billing rendered standalone, outside MainLayout
  - RO setup mounts as a standalone officer shell: expected=RO setup rendered as a standalone officer shell
  - Unauthenticated access to these paths redirects to landing: expected=redirect to `/landing`
  - subscriptionAllowed false forces billing: expected=the SPA forces `/workspace/billing`
  - Onboard, select-guild, and billing do not count as forced away: expected=the force to `/workspace/billing` does not apply; those paths stay
<<<
COMMENT: >>>
domain: Frontend shell/UX
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-170

[REQUIREMENT]
UID: TST-VAL-228
STATUS: Active
TITLE: ApiFetchPaymentRequiredBillingRedirect assigns billing on HTTP 402 unless already there and throws payment-required
STATEMENT: >>>
Plan: ApiFetchPaymentRequiredBillingRedirect assigns billing on HTTP 402 unless already there and throws payment-required
level: unit
verifies: REQ-VAL-171, FNC-VAL-172, UNT-VAL-182, CMP-VAL-004
requires_tol: TOL-ROO-006
patterns: credentials_include, signed_session_headers, http_402_billing, payment_required_throw
execution_status: blocked_on_tooling
evidence_status: none
cases:
  - apiFetch sends credentials include: expected=the request uses credentials:'include'
  - A present session attaches signed profile and tenant headers: expected=signed profile and tenant headers are attached
  - HTTP 402 off the billing path assigns billing: expected=pathname is assigned `/workspace/billing`
  - After the redirect starts, the response error message is thrown: expected=a payment-required error is thrown with that response error message
  - After the redirect starts, a missing message throws the seat-needed default: expected=a payment-required error is thrown with the seat-needed default
  - HTTP 402 already on billing does not count as a redirect: expected=the 402 redirect does not apply; pathname is not assigned
<<<
COMMENT: >>>
domain: Frontend shell/UX
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-171

[REQUIREMENT]
UID: TST-VAL-229
STATUS: Active
TITLE: OnboardLandingSupportComponents matches officer roles, links Discord sign-in by intent, and renders the Valhalla lockup
STATEMENT: >>>
Plan: OnboardLandingSupportComponents matches officer roles, links Discord sign-in by intent, and renders the Valhalla lockup
level: unit
verifies: REQ-VAL-172, FNC-VAL-173, UNT-VAL-183, CMP-VAL-004
requires_tol: TOL-ROO-006
patterns: officer_role_picker, discord_signin_intent, circuit_pause, brand_lockup
execution_status: blocked_on_tooling
evidence_status: none
cases:
  - Officer Role Picker presents Discord guild roles as toggles: expected=Officer Role Picker presents those roles as toggles
  - selectedNames matches case-insensitively: expected=selectedNames counts that role as selected (case-insensitive)
  - An empty selection shows the none-selected hint: expected=the none-selected hint is shown
  - The chosen OAuth intent is remembered: expected=the remembered intent is that choice
  - Discord Sign-In links to auth login with the remembered intent: expected=the link is `/auth/login?intent=signin` for signin and `/auth/login?intent=signup` for signup
  - A circuit or rate-limit block pauses Discord Sign-In: expected=Discord Sign-In is disabled/paused and shows user-facing pause copy
  - Valhalla brand lockup renders logo and mark at sm, md, and lg: expected=product logo and mark render at that size
  - Landing uses the Valhalla lockup and Discord Sign-In: expected=Valhalla lockup and Discord Sign-In (signin and signup) are used
  - Onboard and workspace settings use Officer Role Picker: expected=Officer Role Picker is used for admin/officer role names
<<<
COMMENT: >>>
domain: Frontend shell/UX
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-VAL-172

[[/SECTION]]

[[SECTION]]
TITLE: OCR/GVG Attendance — TST-ROO-230 .. TST-ROO-238 (9 plans)

[REQUIREMENT]
UID: TST-ROO-230
STATUS: Active
TITLE: ListEligibleOcrCalendarEvents lists upcoming plus previous-week events as key/date/title/timeStart, newest date first
STATEMENT: >>>
Plan: ListEligibleOcrCalendarEvents lists upcoming plus previous-week events as key/date/title/timeStart, newest date first
level: system
verifies: REQ-ROO-147, FNC-ROO-142, API-ROO-100, UNT-ROO-152, CMP-ROO-024
requires_tol: TOL-ROO-006
patterns: previous_week, event_row_shape, title_fallback, drop_missing_key, date_desc_title_asc
execution_status: blocked_on_tooling
evidence_status: none
cases:
  - Upcoming instances plus the previous week are eligible: expected=eligible events[] includes those upcoming instances and the previous-week instances
  - A kept event row is key, date, title, and timeStart: expected=the event row is key, date, title, timeStart
  - A missing title falls back to eventId/key: expected=the row title is the eventId/key fallback
  - A row without a key is dropped: expected=that row is not included in eligible events[]
  - Eligible events sort by date descending then title ascending: expected=sorted by date descending, then title ascending (newest-date first)
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-147

[REQUIREMENT]
UID: TST-ROO-231
STATUS: Active
TITLE: ScanPartyScreenshotsDraft accepts limited images, stores a draft, and returns a review id without committing swords
STATEMENT: >>>
Plan: ScanPartyScreenshotsDraft accepts limited images, stores a draft, and returns a review id without committing swords
level: system
verifies: REQ-ROO-148, FNC-ROO-143, API-ROO-101, UNT-ROO-153, CMP-ROO-024
requires_tol: TOL-ROO-006
patterns: scan_limits, draft_only, event_key_400, file_400, review_id
execution_status: blocked_on_tooling
evidence_status: none
cases:
  - A valid scan returns a review id and does not commit swords: expected=a review id is returned; in-game swords are not committed
  - The stored review is a draft from roster name matches: expected=attendance/ocr_reviews/{id} is stored with status draft, ocrMatches, present, absent, unmatched, slotGaps, and occupied from OCR party names matched against that roster
  - Scan images are not primary tenant docs: expected=those images are not stored as primary tenant docs
  - An unresolvable eventKey is 400: expected=400
  - Zero files is 400 with a human message: expected=400 with a human message
  - A non-image file is 400 with a human message: expected=400 with a human message
  - A file over 8MB is 400 with a human message: expected=400 with a human message
  - More than 8 files is 400 with a human message: expected=400 with a human message
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-148

[REQUIREMENT]
UID: TST-ROO-232
STATUS: Active
TITLE: ListOcrReviewsSummaries lists non-cancelled reviews newest-first, capped at 40, as summary cards
STATEMENT: >>>
Plan: ListOcrReviewsSummaries lists non-cancelled reviews newest-first, capped at 40, as summary cards
level: system
verifies: REQ-ROO-149, FNC-ROO-144, API-ROO-102, UNT-ROO-154, CMP-ROO-024
requires_tol: TOL-ROO-006
patterns: exclude_cancelled, created_at_desc, cap_40, summary_card
execution_status: blocked_on_tooling
evidence_status: none
cases:
  - Cancelled reviews are excluded: expected=cancelled reviews are not in the summary cards
  - Non-cancelled reviews are newest createdAt first: expected=summary cards sorted by createdAt descending
  - The list is capped at 40: expected=at most 40 summary cards; reviews past the hard cap of 40 are not returned
  - A summary card carries counts and screenshot pointers: expected=the card has id, status, event fields, present/absent/match/unmatched counts, screenshotUrls/fileNames, and rosterCount
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-149

[REQUIREMENT]
UID: TST-ROO-233
STATUS: Active
TITLE: GetOcrReviewDetailWithRoster returns one review, resolved screenshot URLs, and roster OCR rows, or 404
STATEMENT: >>>
Plan: GetOcrReviewDetailWithRoster returns one review, resolved screenshot URLs, and roster OCR rows, or 404
level: system
verifies: REQ-ROO-149, FNC-ROO-145, API-ROO-103, UNT-ROO-155, CMP-ROO-024
requires_tol: TOL-ROO-006
patterns: missing_404, review_summary, screenshot_urls, roster_rows
execution_status: blocked_on_tooling
evidence_status: none
cases:
  - A missing review is 404: expected=404
  - An existing review returns summary, unmatched, and slotGaps: expected=the review summary, unmatched, and slotGaps
  - Screenshot URLs are resolved: expected=screenshot URLs resolved via staging/CDN helpers
  - Roster rows carry OCR review fields: expected=roster rows with present, ocrState match or unmatch, ocrConfidence, ocrText, and image coords
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-149

[REQUIREMENT]
UID: TST-ROO-234
STATUS: Active
TITLE: PatchDraftPresentOrAssignUnmatched rebuilds present UIDs or assigns unmatched on a draft and rejects non-drafts
STATEMENT: >>>
Plan: PatchDraftPresentOrAssignUnmatched rebuilds present UIDs or assigns unmatched on a draft and rejects non-drafts
level: system
verifies: REQ-ROO-149, REQ-ROO-151, FNC-ROO-146, API-ROO-104, UNT-ROO-156, CMP-ROO-024
requires_tol: TOL-ROO-006
patterns: non_draft_409, present_uids, present_count, assign_unmatched, discord_swallowed
execution_status: blocked_on_tooling
evidence_status: none
cases:
  - A non-draft review is 409: expected=409; the review is not edited
  - presentUids rebuilds present and absent on the stored review: expected=present and absent are rebuilt from the review roster and attendance/ocr_reviews/{id} is persisted
  - The patch returns id and presentCount: expected=the response is id and presentCount
  - unmatchedId and uid assign leftover OCR text: expected=leftover OCR text is mapped to that uid (officer source) and removed from unmatched and slotGaps
  - A Discord refresh error is swallowed: expected=the patch still completes; the Discord error is swallowed
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-149

[REQUIREMENT]
UID: TST-ROO-235
STATUS: Active
TITLE: CommitDraftOcrToInGame finalizes a draft into in-game outcomes, then removes the review
STATEMENT: >>>
Plan: CommitDraftOcrToInGame finalizes a draft into in-game outcomes, then removes the review
level: system
verifies: REQ-ROO-149, REQ-ROO-150, REQ-ROO-151, FNC-ROO-147, API-ROO-105, UNT-ROO-157, CMP-ROO-024
requires_tol: TOL-ROO-006
patterns: non_draft_409, present_uids_before_finalize, status_map, in_game_write, leaf_deleted, gallery, purge, return_notes
execution_status: blocked_on_tooling
evidence_status: none
cases:
  - A non-draft commit is 409: expected=409
  - presentUids are applied before finalize when provided: expected=those presentUids are applied before finalize
  - statusMap is present intersected with the raid roster: expected=statusMap is present ∩ raid roster
  - Commit writes archive or pending swords: expected=commitInGameForEvent writes archive or pending swords
  - The review is marked committed and then the leaf is deleted: expected=the review is marked committed, then attendance/ocr_reviews/{id} is deleted
  - Gallery posts to the raid-screenshot channel when mapped: expected=best-effort postGallery to the raid-screenshot channel
  - Staging is purged and website shots are cleared: expected=purgeReviewStaging and clearWebsiteShots
  - Discord refresh after finalize is best-effort: expected=RefreshDiscordOcrReviewPointer runs best-effort after finalize
  - Commit returns presentCount and swordNote plus galleryNote: expected=presentCount and a human message of swordNote + galleryNote
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-149

[REQUIREMENT]
UID: TST-ROO-236
STATUS: Active
TITLE: CancelDraftOcrReview removes a draft without changing swords and rejects non-drafts
STATEMENT: >>>
Plan: CancelDraftOcrReview removes a draft without changing swords and rejects non-drafts
level: system
verifies: REQ-ROO-149, REQ-ROO-151, FNC-ROO-148, API-ROO-106, UNT-ROO-158, CMP-ROO-024
requires_tol: TOL-ROO-006
patterns: non_draft_409, leaf_removed, cancelled_output, discord_cancelled, no_swords
execution_status: blocked_on_tooling
evidence_status: none
cases:
  - A non-draft cancel is 409: expected=409
  - Cancel removes the review leaf and clears shots and staging: expected=attendance/ocr_reviews/{id} is removed; website shots and staging are cleared
  - Cancel returns cancelled: expected=cancelled
  - Cancel refreshes the Discord pointer as cancelled: expected=RefreshDiscordOcrReviewPointer is called with cancelled status, best-effort
  - Cancel does not change in-game swords: expected=commitInGameForEvent is not called; no in-game sword changes
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-149

[REQUIREMENT]
UID: TST-ROO-237
STATUS: Active
TITLE: DeleteOcrReview deletes a review of any status without changing swords
STATEMENT: >>>
Plan: DeleteOcrReview deletes a review of any status without changing swords
level: system
verifies: REQ-ROO-149, FNC-ROO-149, API-ROO-107, UNT-ROO-159, CMP-ROO-024
requires_tol: TOL-ROO-006
patterns: missing_404, status_agnostic, purge_discord, deleted_output, no_swords
execution_status: blocked_on_tooling
evidence_status: none
cases:
  - A missing review is 404: expected=404
  - Delete has no draft-status guard: expected=both are deleted; a non-draft is not rejected with 409
  - Delete purges the leaf and refreshes Discord as cancelled: expected=the leaf is removed, staging and RAM are purged, and the Discord pointer is refreshed as cancelled
  - Delete returns deleted: expected=deleted
  - Delete does not change in-game swords: expected=no in-game sword changes
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-149

[REQUIREMENT]
UID: TST-ROO-238
STATUS: Active
TITLE: RefreshDiscordOcrReviewPointer edits the Discord review message or no-ops, and does not write swords
STATEMENT: >>>
Plan: RefreshDiscordOcrReviewPointer edits the Discord review message or no-ops, and does not write swords
level: unit
verifies: REQ-ROO-150, FNC-ROO-150, UNT-ROO-160, CMP-VAL-011
requires_tol: TOL-ROO-006
patterns: review_embed, valhalla_link, missing_ids_noop, edit_failure_swallowed, no_swords
execution_status: blocked_on_tooling
evidence_status: none
cases:
  - The pointer embed shows event, OCR counts, and status: expected=the Discord message is edited to an embed showing the event, OCR match/unmatch/O/X counts, and a status line for that status
  - A draft embed includes the Open VALHALLA link: expected=while draft, the embed includes an Open VALHALLA link button
  - Missing channel or message ids are a no-op: expected=no-op; the Discord message is not edited
  - A failed Discord edit is swallowed and does not fail the HTTP writer: expected=no-op; the failure is swallowed and does not fail the HTTP writer that called the refresh
  - The pointer does not write in-game swords: expected=no in-game sword writes
<<<
COMMENT: >>>
domain: OCR/GVG Attendance
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit.
ssot_status: published
HONESTY: published plan only; not executed; no EVD.
<<<
RELATIONS:
- TYPE: Parent
  VALUE: REQ-ROO-150

[[/SECTION]]

[[SECTION]]
TITLE: Platform/Auth gaps — TST-VAL-239 .. TST-VAL-242 (4 plans)

[REQUIREMENT]
UID: TST-VAL-239
STATUS: Active
TITLE: DiscordTokenExchangeBridge uses FRONTEND_URL oauth bridge in production and direct Discord exchange locally
STATEMENT: >>>
Plan: DiscordTokenExchangeBridge uses FRONTEND_URL oauth bridge in production and direct Discord exchange locally
level: unit
verifies: REQ-VAL-008, FNC-VAL-003, UNT-VAL-008, CMP-VAL-002
requires_tol: TOL-ROO-006
patterns: prod_frontend_bridge, local_direct_exchange, token_payload_return
execution_status: blocked_on_tooling
evidence_status: none
cases:
  - Production exchanges the OAuth code through the FRONTEND_URL oauth bridge: expected=code exchange is POST/forwarded through the FRONTEND_URL oauth exchange bridge; Discord does not see the API host IP
  - Local exchanges the OAuth code directly with Discord: expected=exchange goes directly to the Discord token endpoint without the frontend oauth bridge
  - A successful exchange returns token/profile material to the callback handler: expected=Discord token/profile payload is returned to OAuthCallbackHandler
<<<
COMMENT: >>>
domain: Platform/Auth
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit. Does not invent live Vercel↔Discord E2E. bridge failure and Discord token error are listed on the unit without a stated trigger — no cases minted for those codes. REQ says Render IP; unit says API host IP — expected follows the unit.
ssot_status: published
HONESTY: published plan only; not executed; no EVD.
<<<
RELATIONS:
- TYPE: Parent
  VALUE: REQ-VAL-008

[REQUIREMENT]
UID: TST-VAL-240
STATUS: Active
TITLE: CredentialedApiClient uses an empty backend base on localhost and the configured base otherwise
STATEMENT: >>>
Plan: CredentialedApiClient uses an empty backend base on localhost and the configured base otherwise
level: unit
verifies: REQ-VAL-015, FNC-VAL-005, UNT-VAL-014, CMP-VAL-004
requires_tol: TOL-ROO-006
patterns: localhost_empty_base, configured_api_base
execution_status: blocked_on_tooling
evidence_status: none
cases:
  - On localhost the backend base is empty so the proxy serves /api and /auth: expected=backend base URL is empty; request stays same-origin so the Vite proxy can serve /api and /auth; base does not point at a remote host
  - Off localhost the client uses the configured API base URL: expected=client uses the configured API base URL (not the empty localhost base)
<<<
COMMENT: >>>
domain: Platform/Auth
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit. Remaining rules only for REQ-VAL-015. credentials:include and x-user-profile/x-tenant-id header attachment are already cases on published TST-VAL-013 (REQ-VAL-014) — not reminted.
ssot_status: published
HONESTY: published plan only; not executed; no EVD.
<<<
RELATIONS:
- TYPE: Parent
  VALUE: REQ-VAL-015

[REQUIREMENT]
UID: TST-VAL-241
STATUS: Active
TITLE: CorsPolicy allows configured origins with credentials and auth headers, and rejects others without reflecting Origin
STATEMENT: >>>
Plan: CorsPolicy allows configured origins with credentials and auth headers, and rejects others without reflecting Origin
level: unit
verifies: REQ-VAL-017, FNC-VAL-006, UNT-VAL-004, CMP-VAL-001
requires_tol: TOL-ROO-006
patterns: cors_allow_credentials, cors_auth_headers, cors_deny_no_reflect
execution_status: blocked_on_tooling
evidence_status: none
cases:
  - An allowlisted origin is allowed with credentials enabled: expected=CORS allow decision with credentials enabled on the allowed response
  - Preflight/response permits x-user-profile and x-tenant-id: expected=x-user-profile and x-tenant-id are permitted on the preflight/response
  - A disallowed origin is rejected without reflecting that Origin: expected=origin not allowed; Access-Control-Allow-Origin does not echo that Origin as allowed
<<<
COMMENT: >>>
domain: Platform/Auth
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit. Rule-level cases only — does not invent an exhaustive per-host CORS matrix. Client-side header attachment on TST-VAL-013 is a different rule (REQ-VAL-014).
ssot_status: published
HONESTY: published plan only; not executed; no EVD.
<<<
RELATIONS:
- TYPE: Parent
  VALUE: REQ-VAL-017

[REQUIREMENT]
UID: TST-VAL-242
STATUS: Active
TITLE: DocumentTitleController sets product name when logged out or without guild context, and '{Guild} · VALHALLA' when guild-authenticated
STATEMENT: >>>
Plan: DocumentTitleController sets product name when logged out or without guild context, and '{Guild} · VALHALLA' when guild-authenticated
level: unit
verifies: REQ-VAL-018, FNC-VAL-006, UNT-VAL-016, CMP-VAL-004
requires_tol: TOL-ROO-006
patterns: title_logged_out, title_no_guild, title_guild_valhalla
execution_status: blocked_on_tooling
evidence_status: none
cases:
  - Logged out sets the document title to the product name: expected=document.title is the product name
  - No guild context sets the document title to the product name: expected=document.title is the product name (never guild-scoped)
  - Authenticated with guild context sets '{Guild} · VALHALLA': expected=document.title is '{Guild} · VALHALLA'
  - A change in auth or guild context updates the document title to the matching rule: expected=document.title is updated to the product name, or to '{Guild} · VALHALLA' when a guild context is present
<<<
COMMENT: >>>
domain: Platform/Auth
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Disagreement: expected output follows the unit. REQ-VAL-018 names product title only when logged out; unit also applies product title when there is no guild context — expected follows the unit.
ssot_status: published
HONESTY: published plan only; not executed; no EVD.
<<<
RELATIONS:
- TYPE: Parent
  VALUE: REQ-VAL-018

[[/SECTION]]

[[SECTION]]
TITLE: Discord onboarding hub — TST-ROO-243 .. TST-ROO-247, TST-ROO-249, TST-ROO-257 (7 plans)

[REQUIREMENT]
UID: TST-ROO-243
STATUS: Active
TITLE: OnboardingChannelIdField resolves tenant onboardingChannelId and ignores it for setup completeness
STATEMENT: >>>
Plan: OnboardingChannelIdField resolves tenant onboardingChannelId and ignores it for setup completeness
level: unit
verifies: REQ-VAL-075, FNC-VAL-050, UNT-VAL-213, CMP-VAL-007
requires_tol: TOL-ROO-006
patterns: channel_map, no_env_fallback, onboarding_channel
execution_status: blocked_on_tooling
evidence_status: none
cases:
  - A stored onboardingChannelId resolves to that channel id: expected=resolved channel id is the stored tenant_settings.discord_channels.onboardingChannelId value
  - An empty or missing onboardingChannelId stays empty: expected=resolved onboardingChannelId stays empty
  - process.env does not fill an empty onboardingChannelId: expected=alias resolves from the tenant map only; process.env is not read; resolved id stays empty
  - mergeChannelFallback always emits onboardingChannelId: expected=emitted channel fields always include onboardingChannelId among the channel fields
  - Setup completeness ignores onboardingChannelId: expected=onboardingChannelId alone does not complete setup; aucreqChannelId or auctionChannelId or warAnnounceChannelId still completes setup with onboarding empty
<<<
COMMENT: >>>
domain: Discord onboarding
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Reconciles Develop@9237b353 gym plan ids where present; unit wins on disagreement. Gym file tests/cases/unit/TST-ROO-243.test.js. Reconciled verifies away from Develop sdoc (was wrongly REQ-197/FNC-198/UNT-208). New rules vs published TST-VAL-108/UNT-063: onboardingChannelId field, tenant-only DISCORD_ONBOARDING_CHANNEL_ID, mergeChannelFallback emit, setup completeness ignore. Officer Settings/setup entry surfaces are UI — not minted as unit cases.
ssot_status: published
HONESTY: published plan only; not executed; no EVD.
<<<
RELATIONS:
- TYPE: Parent
  VALUE: REQ-VAL-075

[REQUIREMENT]
UID: TST-ROO-244
STATUS: Active
TITLE: DeployOnboardingHub posts or edits the hub via GET /api/deploy-onboarding-card with documented statuses
STATEMENT: >>>
Plan: DeployOnboardingHub posts or edits the hub via GET /api/deploy-onboarding-card with documented statuses
level: system
verifies: REQ-VAL-201, FNC-VAL-202, API-VAL-118, UNT-ROO-212, CMP-VAL-011
requires_tol: TOL-ROO-006
patterns: deploy_onboarding_card, onboarding_channel
execution_status: blocked_on_tooling
evidence_status: none
cases:
  - Officer deploy posts or edits the Onboarding hub on the tenant onboarding channel: expected=server rebuilds hub and posts or edits via sendPublicOnboardingCard/pointer to the tenant-mapped onboarding channel; success returned; process.env channel id is not used
  - Unauthenticated caller returns 401 and does not post: expected=401; no hub posted
  - Non-officer returns 403 and does not post: expected=403; no hub posted
  - Unmapped onboarding channel returns 400 and does not post: expected=400; no hub posted
  - Offline, not connected, rate-limited, or temporarily blocking returns 503 and does not post: expected=503; no hub posted
  - Cannot locate the onboarding channel returns 404 and does not post: expected=404; no hub posted
  - Attendance alias performs the same Discord deploy: expected=same Discord deploy outcome and status mapping as GET /api/deploy-onboarding-card
  - Live handlers do not call evaluateDeployOnboardingGate: expected=handlers use officer checks, deployPublicOnboardingCard, and onboardingDeployHttpStatus; evaluateDeployOnboardingGate is not called
<<<
COMMENT: >>>
domain: Discord onboarding
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Reconciles Develop@9237b353 gym plan ids where present; unit wins on disagreement. Gym file tests/cases/system/TST-ROO-244.test.js. Reconciled verifies to REQ-201/FNC-202/UNT-212 (Develop sdoc had REQ-198/FNC-199). Disagreement (unit wins): gym exercises evaluateDeployOnboardingGate; published UNT-212 rejects that helper for live HTTP — cases follow the unit status mapping and the no-gate rule. No INT-* in verifies (API only at system level, matching prior deploy TSTs).
ssot_status: published
HONESTY: published plan only; not executed; no EVD.
<<<
RELATIONS:
- TYPE: Parent
  VALUE: REQ-VAL-201

[REQUIREMENT]
UID: TST-ROO-245
STATUS: Active
TITLE: PublicOnboardingHubFiveTopics buildHubPayload emits Onboarding title and five non-link topic buttons
STATEMENT: >>>
Plan: PublicOnboardingHubFiveTopics buildHubPayload emits Onboarding title and five non-link topic buttons
level: unit
verifies: REQ-VAL-197, FNC-VAL-198, UNT-ROO-208, CMP-VAL-011
requires_tol: TOL-ROO-006
patterns: onboarding_hub_payload
execution_status: blocked_on_tooling
evidence_status: none
cases:
  - Hub title is Onboarding: expected=embed title is Onboarding
  - Welcome body tells the member to pick a topic: expected=welcome body tells the member to pick a topic for a private explanation and jump
  - Exactly five topic buttons Auction, GvG, General Chat, Website, Message: expected=exactly five topic buttons labeled Auction, GvG, General Chat, Website, Message
  - Topic customIds are onboard auction gvg general website message: expected=customIds are onboard:auction, onboard:gvg, onboard:general, onboard:website, onboard:message
  - Hub topic buttons are not link-style: expected=the five hub topic buttons are not link-style on the hub itself
  - A saved sentence replaces the default purpose: expected=a non-blank discordCardCopy auction sentence replaces the default purpose text
  - Message jumps to messageChannelId: expected=Message topic title is Message; body mentions the mapped channel; Jump to channel uses messageChannelId; Back present
  - Blank card copy falls back to the default sentence: expected=blank request and message sentences resolve to the built-in defaults
<<<
COMMENT: >>>
domain: Discord onboarding
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Reconciles Develop@9237b353 gym plan ids where present; unit wins on disagreement. Gym file tests/cases/unit/TST-ROO-245.test.js. Reconciled verifies to UNT-208/FNC-198/REQ-197/CMP-011 (Develop sdoc wrongly pointed at UNT-209/CMP-010).
ssot_status: published
HONESTY: published plan only; not executed; no EVD.
<<<
RELATIONS:
- TYPE: Parent
  VALUE: REQ-VAL-197

[REQUIREMENT]
UID: TST-ROO-246
STATUS: Active
TITLE: OnboardingTopicCards buildTopicPayload explains purpose with jump, unmapped sentence, or Open VALHALLA
STATEMENT: >>>
Plan: OnboardingTopicCards buildTopicPayload explains purpose with jump, unmapped sentence, or Open VALHALLA
level: unit
verifies: REQ-VAL-198, FNC-VAL-199, UNT-ROO-209, CMP-VAL-011
requires_tol: TOL-ROO-006
patterns: onboarding_topic_payload
execution_status: blocked_on_tooling
evidence_status: none
cases:
  - Mapped Auction/GvG/General Chat/Message topics resolve the matching channel field: expected=title matches topic; body includes that topic's purpose text and channel mention; Jump to channel link is https://discord.com/channels/{guildId}/{channelId}; Back present; Message uses messageChannelId
  - Unmapped Discord topic has the officer-paste sentence and no jump: expected=body includes 'This channel is not mapped yet. Ask an officer to paste the ID in Settings.'; no jump link; Back present
  - Website Open VALHALLA uses frontend origin without trailing slash: expected=purpose text present; Open VALHALLA link URL is that origin with trailing slash removed; Back present
  - Empty frontend origin offers no Open VALHALLA link: expected=no Open VALHALLA link; Back always present
  - Back customId is onboard:back: expected=Back control customId is onboard:back
<<<
COMMENT: >>>
domain: Discord onboarding
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Reconciles Develop@9237b353 gym plan ids where present; unit wins on disagreement. Gym file tests/cases/unit/TST-ROO-246.test.js. Reconciled verifies to UNT-209/FNC-199/REQ-198/CMP-011. Do not invent Discord sentence text beyond the published unmapped Settings sentence.
ssot_status: published
HONESTY: published plan only; not executed; no EVD.
<<<
RELATIONS:
- TYPE: Parent
  VALUE: REQ-VAL-198

[REQUIREMENT]
UID: TST-ROO-247
STATUS: Active
TITLE: OnboardingAckEphemeralOrUpdate chooses ephemeral defer-reply from hub and defer-update when already ephemeral
STATEMENT: >>>
Plan: OnboardingAckEphemeralOrUpdate chooses ephemeral defer-reply from hub and defer-update when already ephemeral
level: unit
verifies: REQ-VAL-199, FNC-VAL-200, UNT-ROO-210, CMP-VAL-011
requires_tol: TOL-ROO-006
patterns: onboarding_ack
execution_status: blocked_on_tooling
evidence_status: none
cases:
  - Public hub known topic is ephemeral defer-reply then topic card: expected=ack is ephemeral defer-reply; reply is edited to that topic card
  - Already-ephemeral topic or Back is defer-update in place: expected=ack is defer-update; same message edited to the topic or hub; Back does not post a new public hub message
  - Unknown onboard customId is ignored with no ACK: expected=ignored; no ACK
<<<
COMMENT: >>>
domain: Discord onboarding
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Reconciles Develop@9237b353 gym plan ids where present; unit wins on disagreement. Gym file tests/cases/unit/TST-ROO-247.test.js. Reconciled verifies to UNT-210/FNC-200/REQ-199/CMP-011 (Develop sdoc wrongly pointed at UNT-211). Gateway onboard: routing is CMP-010 soft note — no separate interaction INT minted.
ssot_status: published
HONESTY: published plan only; not executed; no EVD.
<<<
RELATIONS:
- TYPE: Parent
  VALUE: REQ-VAL-199

[REQUIREMENT]
UID: TST-ROO-249
STATUS: Active
TITLE: OnboardingHubPointerRedeploy edits the stored hub message when possible else sends a new hub
STATEMENT: >>>
Plan: OnboardingHubPointerRedeploy edits the stored hub message when possible else sends a new hub
level: unit
verifies: REQ-VAL-200, FNC-VAL-201, UNT-ROO-211, CMP-VAL-011
requires_tol: TOL-ROO-006
patterns: onboarding_card_pointer
execution_status: blocked_on_tooling
evidence_status: none
cases:
  - Pointer is stored at attendance/onboarding_card with channelId, messageId, updatedAt: expected=attendance/onboarding_card is written with channelId, messageId, and updatedAt
  - Edit is attempted only when stored channelId matches target and messageId is present: expected=edit path is taken only when stored channelId equals the target channel id and messageId is present; otherwise send path
  - When Discord still has the message, edit the hub and refresh the pointer: expected=existing hub message is edited to the hub payload; pointer refreshed; no new public message required
  - Fetch or edit failure sends a new hub and updates the pointer: expected=a new hub message is sent; pointer updated to the new messageId
<<<
COMMENT: >>>
domain: Discord onboarding
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done. Reconciles Develop@9237b353 gym plan ids where present; unit wins on disagreement. No matching gym case on Develop@9237b353 (243–247 exist; 248 is GvG — left alone). Minted next free after leaving 248 unused by this slice.
ssot_status: published
HONESTY: published plan only; not executed; no EVD.
<<<
RELATIONS:
- TYPE: Parent
  VALUE: REQ-VAL-200

[REQUIREMENT]
UID: TST-ROO-257
STATUS: Active
TITLE: Onboarding hub deploy needs Origin enabled and an active seat and touches only Origin data and cards
STATEMENT: >>>
Plan: Onboarding hub deploy needs Origin enabled and an active seat and touches only Origin data and cards
level: system
verifies: REQ-VAL-050, REQ-VAL-211, FNC-VAL-202, API-VAL-118, UNT-ROO-212, CMP-VAL-011
requires_tol: TOL-ROO-006
patterns: deploy_game_gate, seat_required, origin_card_pointer
execution_status: blocked_on_tooling
evidence_status: none
cases:
  - Without Origin enabled the deploy is refused: expected=403 {code: 'game_required', gameId: 'ragnarok-origin'}; no hub posted
  - Ragnarok 3 enabled alone does not count: expected=403 game_required naming ragnarok-origin; no hub posted
  - An inactive seat is 402: expected=402 {code: 'payment_required'}; no hub posted
  - An accepted deploy keeps its pointer as Origin data: expected=game ragnarok-origin set; hub pointer read and written as Origin data
  - No Ragnarok 3 card or record changes: expected=Ragnarok 3 message and every Ragnarok 3 record unchanged
<<<
COMMENT: >>>
domain: Discord onboarding
notes: verifies = planned lineage only; published ≠ proven. Last Boss owns EVD. No depends_on. No EVD. evidence_status=none. execution_status=blocked_on_tooling. requires_tol is a node field only (TOL-ROO-006 Vitest cataloged, greenfield); do not claim tests can run. No cross-project verifies; Ragnarok 3 counterparts are text only. Vocabulary: planned lineage only; never covered/passed/done. Code at f38e137 (cited only): backend/src/createApp.js:135, 165, 181, 197 and 213 guard the root deploy routes with requireOfficerTenant only (no game gate; they run with no game set and fall back to Origin), so the game-gate cases are expected to fail at f38e137 (code gap on FNC-VAL-045..048, FNC-VAL-202, API-VAL-024..027, API-VAL-118). Status mapping cases stay in TST-ROO-244. Root onboarding deploy carries the seat check per UNT-ROO-212 invariant and API-VAL-118; the four other root deploys do not (UNT-VAL-058..061).
ssot_status: published
HONESTY: published plan only; not executed; no EVD.
<<<
RELATIONS:
- TYPE: Parent
  VALUE: REQ-VAL-050

[[/SECTION]]

[[SECTION]]
TITLE: GVG Readiness rematerialize — TST-ROO-248 (1 plan)

[REQUIREMENT]
UID: TST-ROO-248
STATUS: Active
TITLE: GvgReadinessSyncMode rematerializes once at Preparation start
STATEMENT: >>>
Plan: GvgReadinessSyncMode rematerializes once at Preparation start
level: unit
verifies: REQ-VAL-200, FNC-VAL-201, UNT-VAL-213, INT-ROO-117, CMP-ROO-020
requires_tol: TOL-ROO-006
patterns: gvg_readiness_sync, readiness_board_gate
execution_status: blocked_on_tooling
evidence_status: none
cases:
  - Phase 1 with a matching stored eventKey and messageId is skip: expected=gvgReadinessSyncMode returns skip
  - Phase 1 with last week’s eventKey is rematerialize: expected=gvgReadinessSyncMode returns rematerialize
  - Phase 1 with no stored pointer is rematerialize: expected=gvgReadinessSyncMode returns rematerialize
  - Phase 2 or 3 is ifMissing: expected=gvgReadinessSyncMode returns ifMissing
  - A non-prep phase is skip: expected=gvgReadinessSyncMode returns skip
  - Phase 1 + successful publish + last week’s eventKey rematerializes: expected=ensureGvgReadinessBoard runs; ensureGvgReadinessBoardIfMissing does not
  - Phase 1 + successful publish + this cycle’s eventKey skips the board: expected=neither ensureGvgReadinessBoard nor ensureGvgReadinessBoardIfMissing runs
  - Phase 2 with a stored messageId uses IfMissing: expected=ensureGvgReadinessBoardIfMissing runs; ensureGvgReadinessBoard does not
  - A failed publish does not call either board function: expected=ensureGvgReadinessBoardIfMissing does not run; ensureGvgReadinessBoard does not run
<<<
COMMENT: >>>
domain: Discord bot/Channels
notes: verifies = planned lineage only; published ≠ proven. Last Boss owns EVD. No depends_on. No EVD. evidence_status=none. execution_status=blocked_on_tooling. requires_tol is a node field only (TOL-ROO-006 Vitest cataloged, greenfield); do not claim tests can run. Vocabulary: planned lineage only; never covered/passed/done.
ssot_status: published
HONESTY: published plan only; not executed; no EVD.
<<<
RELATIONS:
- TYPE: Parent
  VALUE: REQ-VAL-200

[[/SECTION]]

[[SECTION]]
TITLE: Ragnarok 3 — TST-R3-001 .. TST-R3-005

[REQUIREMENT]
UID: TST-R3-001
STATUS: Active
TITLE: RequireGameGate returns 403 game_required for Ragnarok 3 mounts
STATEMENT: >>>
Plan: RequireGameGate returns 403 game_required for Ragnarok 3 mounts
level: unit
verifies: REQ-R3-005, REQ-VAL-046
requires_tol: TOL-ROO-006
patterns: require_game_gate, r3_game_required, unit_require_game_mount_tree
execution_status: blocked_on_tooling
evidence_status: none
cases:
  - R3 middleware without ragnarok-3 → 403 game_required: expected=code game_required, gameId ragnarok-3
  - R3 API tree without ragnarok-3 → 403 game_required: expected=/api/ragnarok-3/health 403 game_required
<<<
COMMENT: >>>
domain: Ragnarok 3
notes: verifies = planned lineage only; published ≠ proven. evidence_status=none. execution_status=blocked_on_tooling.
ssot_status: published
HONESTY: published plan only; not executed; no EVD.
<<<
RELATIONS:
- TYPE: Parent
  VALUE: REQ-R3-005

[REQUIREMENT]
UID: TST-R3-002
STATUS: Active
TITLE: Dual roster allows the same discord_id on Origin and R3
STATEMENT: >>>
Plan: Dual roster allows the same discord_id on Origin and R3
level: unit
verifies: REQ-R3-002, REQ-R3-003
requires_tol: TOL-ROO-006
patterns: r3_dual_roster
execution_status: blocked_on_tooling
evidence_status: none
cases:
  - two members rows for the same discord_id with distinct game_id: expected=INSERT members twice with ragnarok-origin then ragnarok-3
<<<
COMMENT: >>>
domain: Ragnarok 3
notes: verifies = planned lineage only; published ≠ proven. evidence_status=none. execution_status=blocked_on_tooling.
ssot_status: published
HONESTY: published plan only; not executed; no EVD.
<<<
RELATIONS:
- TYPE: Parent
  VALUE: REQ-R3-003

[REQUIREMENT]
UID: TST-R3-003
STATUS: Active
TITLE: R3 settings save does not mutate Origin game_settings or workspace
STATEMENT: >>>
Plan: R3 settings save does not mutate Origin game_settings or workspace
level: unit
verifies: REQ-R3-004
requires_tol: TOL-ROO-006
patterns: r3_settings_split
execution_status: blocked_on_tooling
evidence_status: none
cases:
  - writes game_settings for ragnarok-3 only and omits workspace keys: expected=no tenant_settings write; no Origin game_settings write
<<<
COMMENT: >>>
domain: Ragnarok 3
notes: verifies = planned lineage only; published ≠ proven. evidence_status=none. execution_status=blocked_on_tooling.
ssot_status: published
HONESTY: published plan only; not executed; no EVD.
<<<
RELATIONS:
- TYPE: Parent
  VALUE: REQ-R3-004

[REQUIREMENT]
UID: TST-R3-004
STATUS: Active
TITLE: Operational rows are stamped with game_id and Origin backfill exists
STATEMENT: >>>
Plan: Operational rows are stamped with game_id and Origin backfill exists
level: unit
verifies: REQ-R3-002, REQ-VAL-158, REQ-VAL-160, REQ-VAL-161
requires_tol: TOL-ROO-006
patterns: r3_game_id_stamp, schema_migrate
execution_status: blocked_on_tooling
evidence_status: none
cases:
  - schema adds game_settings, game_id PKs, Origin backfill, and AG json_docs stamp: expected=schema.sql contains backfill and PK rebuild
  - R3 json_docs writes stamp game_id ragnarok-3 on Origin-shaped paths: expected=INSERT json_docs game_id ragnarok-3 path attendance/compositions
<<<
COMMENT: >>>
domain: Ragnarok 3
notes: verifies = planned lineage only; published ≠ proven. evidence_status=none. execution_status=blocked_on_tooling.
ssot_status: published
HONESTY: published plan only; not executed; no EVD.
<<<
RELATIONS:
- TYPE: Parent
  VALUE: REQ-R3-002

[REQUIREMENT]
UID: TST-R3-005
STATUS: Active
TITLE: R3 calendar does not leak into scheduleContributors
STATEMENT: >>>
Plan: R3 calendar does not leak into scheduleContributors
level: unit
verifies: REQ-R3-006, REQ-R3-007
requires_tol: TOL-ROO-006
patterns: r3_no_schedule_contributor, r3_path_catalog
execution_status: blocked_on_tooling
evidence_status: none
cases:
  - no ragnarok-3 contributor is registered: expected=CONTRIBUTORS has no ragnarok-3 key
  - leftover Origin root paths still resolve to Origin: expected=gameIdForPath(/attendance/masterlist) → ragnarok-origin
<<<
COMMENT: >>>
domain: Ragnarok 3
notes: verifies = planned lineage only; published ≠ proven. evidence_status=none. execution_status=blocked_on_tooling.
ssot_status: published
HONESTY: published plan only; not executed; no EVD.
<<<
RELATIONS:
- TYPE: Parent
  VALUE: REQ-R3-007

[REQUIREMENT]
UID: TST-R3-006
STATUS: Active
TITLE: R3 API tree without ragnarok-3 returns 403 game_required
STATEMENT: >>>
Plan: R3 API tree without ragnarok-3 returns 403 game_required
level: unit
verifies: REQ-R3-005
requires_tol: TOL-ROO-006
patterns: unit_require_game_mount_tree, r3_game_required
execution_status: blocked_on_tooling
evidence_status: none
cases:
  - R3 API tree without ragnarok-3 → 403 game_required: expected=/api/ragnarok-3/health 403 game_required
<<<
COMMENT: >>>
domain: Ragnarok 3
notes: verifies = planned lineage only; published ≠ proven. evidence_status=none. execution_status=blocked_on_tooling.
ssot_status: published
HONESTY: published plan only; not executed; no EVD.
<<<
RELATIONS:
- TYPE: Parent
  VALUE: REQ-R3-005

[[/SECTION]]
