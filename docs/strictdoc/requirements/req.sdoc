[DOCUMENT]
TITLE: ROO System Requirements (REQ)
UID: DOC-ROO-REQ
VERSION: 0.1
OPTIONS:
  MARKUP: Text

[[SECTION]]
TITLE: About

[TEXT]
STATEMENT: >>>
Project: ROO / ROOGuildApp.
SoT: Develop@a8a1edd713d6db6db61d42ed4eacf6a9e8737d07.
Source: SSOT requirements/req (published only).
Each REQ Parent-links to its USR via linked_from.
Poison: Requirements/Requirements.md is NOT SoT.
Phase 1 complete: 172 REQ nodes (numeric 001 .. 172). Platform domains use VAL; Origin game domains stay ROO.
published ≠ proven; zero EVD at export time.
SSOT sync 2026-10-10 (JST): graph 91; source xWhiteSpace/ROOGuildApp@f38e1378c7cca457fbf8de8e8355d59994f77fc8. Published REQ: 211 (VAL 106, ROO 105). Ragnarok 3 REQs live in requirements/ro3_req.sdoc (RO3 project). The 'Ragnarok 3 (REQ-R3-…)' section below is Staging-authored legacy text kept as-is; it is not an SSOT node set. Published in SSOT ≠ proven; no EVD; every TST is execution_status blocked_on_tooling, evidence_status none.
<<<

[[/SECTION]]

[[SECTION]]
TITLE: Platform/Auth (REQ-VAL-001 .. REQ-VAL-020)

[REQUIREMENT]
UID: REQ-VAL-001
STATUS: Active
TITLE: REQ-VAL-001: GET / returns an online body when the database ping succeeds, and returns HTTP 5
STATEMENT: >>>
GET / returns an online body when the database ping succeeds, and returns HTTP 503 with a failure body when the database ping fails.
<<<
COMMENT: >>>
domain: Platform/Auth
priority: must
type: system
constraints: Live Develop behavior only; Do not import Firebase Requirements.md wording
acceptance_criteria: GET / returns an online body when the database ping succeeds, and returns HTTP 503 with a failure body when the database ping fails.
source_draft: D-REQ-001
ssot_status: published
sot: Develop@a8a1edd713d6db6db61d42ed4eacf6a9e8737d07
<<<
RELATIONS:
- TYPE: Parent
  VALUE: USR-VAL-001

[REQUIREMENT]
UID: REQ-VAL-002
STATUS: Active
TITLE: REQ-VAL-002: Backend process exits/refuses normal start unless Discord OAuth client credentia
STATEMENT: >>>
Backend process exits/refuses normal start unless Discord OAuth client credentials, bot token, OAUTH_REDIRECT_URI, SESSION_SECRET, and DATABASE_URL are present (env.js gate).
<<<
COMMENT: >>>
domain: Platform/Auth
priority: must
type: system
constraints: Live Develop behavior only; Do not import Firebase Requirements.md wording
acceptance_criteria: Backend process exits/refuses normal start unless Discord OAuth client credentials, bot token, OAUTH_REDIRECT_URI, SESSION_SECRET, and DATABASE_URL are present (env.js gate).
source_draft: D-REQ-002
ssot_status: published
sot: Develop@a8a1edd713d6db6db61d42ed4eacf6a9e8737d07
<<<
RELATIONS:
- TYPE: Parent
  VALUE: USR-VAL-001

[REQUIREMENT]
UID: REQ-VAL-003
STATUS: Active
TITLE: REQ-VAL-003: On successful start, backend runs migrate() before initializing the Discord bot.
STATEMENT: >>>
On successful start, backend runs migrate() before initializing the Discord bot.
<<<
COMMENT: >>>
domain: Platform/Auth
priority: must
type: system
constraints: Live Develop behavior only; Do not import Firebase Requirements.md wording
acceptance_criteria: On successful start, backend runs migrate() before initializing the Discord bot.
source_draft: D-REQ-003
ssot_status: published
sot: Develop@a8a1edd713d6db6db61d42ed4eacf6a9e8737d07
<<<
RELATIONS:
- TYPE: Parent
  VALUE: USR-VAL-001

[REQUIREMENT]
UID: REQ-VAL-004
STATUS: Active
TITLE: REQ-VAL-004: GET /auth/login redirects to Discord OAuth authorizing scopes identify, guilds, 
STATEMENT: >>>
GET /auth/login redirects to Discord OAuth authorizing scopes identify, guilds, and guilds.members.read, carrying state intent signin or signup.
<<<
COMMENT: >>>
domain: Platform/Auth
priority: must
type: system
constraints: Live Develop behavior only; Do not import Firebase Requirements.md wording
acceptance_criteria: GET /auth/login redirects to Discord OAuth authorizing scopes identify, guilds, and guilds.members.read, carrying state intent signin or signup.
source_draft: D-REQ-004
ssot_status: published
sot: Develop@a8a1edd713d6db6db61d42ed4eacf6a9e8737d07
<<<
RELATIONS:
- TYPE: Parent
  VALUE: USR-VAL-002

[REQUIREMENT]
UID: REQ-VAL-005
STATUS: Active
TITLE: REQ-VAL-005: GET /auth/callback exchanges the OAuth code, persists a compact Discord guild li
STATEMENT: >>>
GET /auth/callback exchanges the OAuth code, persists a compact Discord guild list into session and DB, and builds the base user identity.
<<<
COMMENT: >>>
domain: Platform/Auth
priority: must
type: system
constraints: Live Develop behavior only; Do not import Firebase Requirements.md wording
acceptance_criteria: GET /auth/callback exchanges the OAuth code, persists a compact Discord guild list into session and DB, and builds the base user identity.
source_draft: D-REQ-005
ssot_status: published
sot: Develop@a8a1edd713d6db6db61d42ed4eacf6a9e8737d07
<<<
RELATIONS:
- TYPE: Parent
  VALUE: USR-VAL-002

[REQUIREMENT]
UID: REQ-VAL-006
STATUS: Active
TITLE: REQ-VAL-006: When OAuth callback finds exactly one onboarded guild and intent is not signup, 
STATEMENT: >>>
When OAuth callback finds exactly one onboarded guild and intent is not signup, the user is redirected into that tenant path (home, billing, or onboard as applicable).
<<<
COMMENT: >>>
domain: Platform/Auth
priority: must
type: system
constraints: Live Develop behavior only; Do not import Firebase Requirements.md wording
acceptance_criteria: When OAuth callback finds exactly one onboarded guild and intent is not signup, the user is redirected into that tenant path (home, billing, or onboard as applicable).
source_draft: D-REQ-006
ssot_status: published
sot: Develop@a8a1edd713d6db6db61d42ed4eacf6a9e8737d07
<<<
RELATIONS:
- TYPE: Parent
  VALUE: USR-VAL-002

[REQUIREMENT]
UID: REQ-VAL-007
STATUS: Active
TITLE: REQ-VAL-007: When OAuth callback finds zero or multiple onboarded guilds, or intent is signup
STATEMENT: >>>
When OAuth callback finds zero or multiple onboarded guilds, or intent is signup, the user is redirected to /select-guild with auth_user context.
<<<
COMMENT: >>>
domain: Platform/Auth
priority: must
type: system
constraints: Live Develop behavior only; Do not import Firebase Requirements.md wording
acceptance_criteria: When OAuth callback finds zero or multiple onboarded guilds, or intent is signup, the user is redirected to /select-guild with auth_user context.
source_draft: D-REQ-007
ssot_status: published
sot: Develop@a8a1edd713d6db6db61d42ed4eacf6a9e8737d07
<<<
RELATIONS:
- TYPE: Parent
  VALUE: USR-VAL-002

[REQUIREMENT]
UID: REQ-VAL-008
STATUS: Active
TITLE: REQ-VAL-008: In production, Discord token exchange goes through the Vercel FRONTEND_URL oauth
STATEMENT: >>>
In production, Discord token exchange goes through the Vercel FRONTEND_URL oauth exchange bridge so Discord never sees the Render IP; local development may exchange directly.
<<<
COMMENT: >>>
domain: Platform/Auth
priority: must
type: system
constraints: Live Develop behavior only; Do not import Firebase Requirements.md wording
acceptance_criteria: In production, Discord token exchange goes through the Vercel FRONTEND_URL oauth exchange bridge so Discord never sees the Render IP; local development may exchange directly.
source_draft: D-REQ-008
ssot_status: published
sot: Develop@a8a1edd713d6db6db61d42ed4eacf6a9e8737d07
<<<
RELATIONS:
- TYPE: Parent
  VALUE: USR-VAL-002

[REQUIREMENT]
UID: REQ-VAL-009
STATUS: Active
TITLE: REQ-VAL-009: When the Discord circuit is open, login and callback redirect to landing with di
STATEMENT: >>>
When the Discord circuit is open, login and callback redirect to landing with discord_rate_limited (including until hint) instead of completing OAuth.
<<<
COMMENT: >>>
domain: Platform/Auth
priority: must
type: system
constraints: Live Develop behavior only; Do not import Firebase Requirements.md wording
acceptance_criteria: When the Discord circuit is open, login and callback redirect to landing with discord_rate_limited (including until hint) instead of completing OAuth.
source_draft: D-REQ-009
ssot_status: published
sot: Develop@a8a1edd713d6db6db61d42ed4eacf6a9e8737d07
<<<
RELATIONS:
- TYPE: Parent
  VALUE: USR-VAL-002

[REQUIREMENT]
UID: REQ-VAL-010
STATUS: Active
TITLE: REQ-VAL-010: GET /auth/me returns {authenticated,user} with a re-signed profile when authenti
STATEMENT: >>>
GET /auth/me returns {authenticated,user} with a re-signed profile when authenticated; returns authenticated:false when not.
<<<
COMMENT: >>>
domain: Platform/Auth
priority: must
type: system
constraints: Live Develop behavior only; Do not import Firebase Requirements.md wording
acceptance_criteria: GET /auth/me returns {authenticated,user} with a re-signed profile when authenticated; returns authenticated:false when not.
source_draft: D-REQ-010
ssot_status: published
sot: Develop@a8a1edd713d6db6db61d42ed4eacf6a9e8737d07
<<<
RELATIONS:
- TYPE: Parent
  VALUE: USR-VAL-003

[REQUIREMENT]
UID: REQ-VAL-011
STATUS: Active
TITLE: REQ-VAL-011: POST /auth/logout destroys the server session and clears the connect.sid cookie.
STATEMENT: >>>
POST /auth/logout destroys the server session and clears the connect.sid cookie.
<<<
COMMENT: >>>
domain: Platform/Auth
priority: must
type: system
constraints: Live Develop behavior only; Do not import Firebase Requirements.md wording
acceptance_criteria: POST /auth/logout destroys the server session and clears the connect.sid cookie.
source_draft: D-REQ-011
ssot_status: published
sot: Develop@a8a1edd713d6db6db61d42ed4eacf6a9e8737d07
<<<
RELATIONS:
- TYPE: Parent
  VALUE: USR-VAL-003

[REQUIREMENT]
UID: REQ-VAL-012
STATUS: Active
TITLE: REQ-VAL-012: Identity resolution prefers session user; otherwise accepts HMAC-signed x-user-p
STATEMENT: >>>
Identity resolution prefers session user; otherwise accepts HMAC-signed x-user-profile verified with DISCORD_CLIENT_SECRET.
<<<
COMMENT: >>>
domain: Platform/Auth
priority: must
type: system
constraints: Live Develop behavior only; Do not import Firebase Requirements.md wording
acceptance_criteria: Identity resolution prefers session user; otherwise accepts HMAC-signed x-user-profile verified with DISCORD_CLIENT_SECRET.
source_draft: D-REQ-012
ssot_status: published
sot: Develop@a8a1edd713d6db6db61d42ed4eacf6a9e8737d07
<<<
RELATIONS:
- TYPE: Parent
  VALUE: USR-VAL-003

[REQUIREMENT]
UID: REQ-VAL-013
STATUS: Active
TITLE: REQ-VAL-013: SPA restores session from auth_user query first, then guild_raid_session localSt
STATEMENT: >>>
SPA restores session from auth_user query first, then guild_raid_session localStorage (migrating legacy dynasty_raid_session if present), then verifies with GET /auth/me.
<<<
COMMENT: >>>
domain: Platform/Auth
priority: must
type: software
constraints: Live Develop behavior only; Do not import Firebase Requirements.md wording
acceptance_criteria: SPA restores session from auth_user query first, then guild_raid_session localStorage (migrating legacy dynasty_raid_session if present), then verifies with GET /auth/me.
source_draft: D-REQ-013
ssot_status: published
sot: Develop@a8a1edd713d6db6db61d42ed4eacf6a9e8737d07
<<<
RELATIONS:
- TYPE: Parent
  VALUE: USR-VAL-004

[REQUIREMENT]
UID: REQ-VAL-014
STATUS: Active
TITLE: REQ-VAL-014: SPA apiFetch always uses credentials:'include' and attaches x-user-profile and x
STATEMENT: >>>
SPA apiFetch always uses credentials:'include' and attaches x-user-profile and x-tenant-id headers when a session exists.
<<<
COMMENT: >>>
domain: Platform/Auth
priority: must
type: software
constraints: Live Develop behavior only; Do not import Firebase Requirements.md wording
acceptance_criteria: SPA apiFetch always uses credentials:'include' and attaches x-user-profile and x-tenant-id headers when a session exists.
source_draft: D-REQ-014
ssot_status: published
sot: Develop@a8a1edd713d6db6db61d42ed4eacf6a9e8737d07
<<<
RELATIONS:
- TYPE: Parent
  VALUE: USR-VAL-004

[REQUIREMENT]
UID: REQ-VAL-015
STATUS: Active
TITLE: REQ-VAL-015: On localhost, SPA uses an empty backend base so Vite proxies /api and /auth.
STATEMENT: >>>
On localhost, SPA uses an empty backend base so Vite proxies /api and /auth.
<<<
COMMENT: >>>
domain: Platform/Auth
priority: must
type: software
constraints: Live Develop behavior only; Do not import Firebase Requirements.md wording
acceptance_criteria: On localhost, SPA uses an empty backend base so Vite proxies /api and /auth.
source_draft: D-REQ-015
ssot_status: published
sot: Develop@a8a1edd713d6db6db61d42ed4eacf6a9e8737d07
<<<
RELATIONS:
- TYPE: Parent
  VALUE: USR-VAL-004

[REQUIREMENT]
UID: REQ-VAL-016
STATUS: Active
TITLE: REQ-VAL-016: Session cookies use secure:false and sameSite:lax on local HTTP; deployed HTTPS 
STATEMENT: >>>
Session cookies use secure:false and sameSite:lax on local HTTP; deployed HTTPS uses secure:true and sameSite:none.
<<<
COMMENT: >>>
domain: Platform/Auth
priority: must
type: system
constraints: Live Develop behavior only; Do not import Firebase Requirements.md wording
acceptance_criteria: Session cookies use secure:false and sameSite:lax on local HTTP; deployed HTTPS uses secure:true and sameSite:none.
source_draft: D-REQ-016
ssot_status: published
sot: Develop@a8a1edd713d6db6db61d42ed4eacf6a9e8737d07
<<<
RELATIONS:
- TYPE: Parent
  VALUE: USR-VAL-005

[REQUIREMENT]
UID: REQ-VAL-017
STATUS: Active
TITLE: REQ-VAL-017: CORS allows configured FRONTEND_URL, localhost, known dynasty hosts, *.vercel.ap
STATEMENT: >>>
CORS allows configured FRONTEND_URL, localhost, known dynasty hosts, *.vercel.app, LAN, and ngrok; credentials enabled; allows headers x-user-profile and x-tenant-id.
<<<
COMMENT: >>>
domain: Platform/Auth
priority: must
type: system
constraints: Live Develop behavior only; Do not import Firebase Requirements.md wording
acceptance_criteria: CORS allows configured FRONTEND_URL, localhost, known dynasty hosts, *.vercel.app, LAN, and ngrok; credentials enabled; allows headers x-user-profile and x-tenant-id.
source_draft: D-REQ-017
ssot_status: published
sot: Develop@a8a1edd713d6db6db61d42ed4eacf6a9e8737d07
<<<
RELATIONS:
- TYPE: Parent
  VALUE: USR-VAL-005

[REQUIREMENT]
UID: REQ-VAL-018
STATUS: Active
TITLE: REQ-VAL-018: Document title is the product name when logged out and '{Guild} · VALHALLA' when
STATEMENT: >>>
Document title is the product name when logged out and '{Guild} · VALHALLA' when authenticated with a guild context.
<<<
COMMENT: >>>
domain: Platform/Auth
priority: should
type: software
constraints: Live Develop behavior only; Do not import Firebase Requirements.md wording
acceptance_criteria: Document title is the product name when logged out and '{Guild} · VALHALLA' when authenticated with a guild context.
source_draft: D-REQ-018
ssot_status: published
sot: Develop@a8a1edd713d6db6db61d42ed4eacf6a9e8737d07
<<<
RELATIONS:
- TYPE: Parent
  VALUE: USR-VAL-005

[REQUIREMENT]
UID: REQ-VAL-019
STATUS: Active
TITLE: REQ-VAL-019: /login permanently redirects to /landing.
STATEMENT: >>>
/login permanently redirects to /landing.
<<<
COMMENT: >>>
domain: Platform/Auth
priority: must
type: software
constraints: Live Develop behavior only; Do not import Firebase Requirements.md wording
acceptance_criteria: /login permanently redirects to /landing.
source_draft: D-REQ-019
ssot_status: published
sot: Develop@a8a1edd713d6db6db61d42ed4eacf6a9e8737d07
<<<
RELATIONS:
- TYPE: Parent
  VALUE: USR-VAL-005

[REQUIREMENT]
UID: REQ-VAL-020
STATUS: Active
TITLE: REQ-VAL-020: Unauthenticated users navigating protected shells are redirected to /landing.
STATEMENT: >>>
Unauthenticated users navigating protected shells are redirected to /landing.
<<<
COMMENT: >>>
domain: Platform/Auth
priority: must
type: software
constraints: Live Develop behavior only; Do not import Firebase Requirements.md wording
acceptance_criteria: Unauthenticated users navigating protected shells are redirected to /landing.
source_draft: D-REQ-020
ssot_status: published
sot: Develop@a8a1edd713d6db6db61d42ed4eacf6a9e8737d07
<<<
RELATIONS:
- TYPE: Parent
  VALUE: USR-VAL-005

[[/SECTION]]

[[SECTION]]
TITLE: Tenant/Workspace (REQ-VAL-021 .. REQ-VAL-038)

[REQUIREMENT]
UID: REQ-VAL-021
STATUS: Active
TITLE: REQ-VAL-021: One Discord guild id is the tenant primary key (`tenants.id`).
STATEMENT: >>>
One Discord guild id is the tenant primary key (`tenants.id`).
<<<
COMMENT: >>>
domain: Tenant/Workspace
priority: must
type: system
constraints: Live Develop behavior only; Do not import Firebase Requirements.md wording
acceptance_criteria: One Discord guild id is the tenant primary key (`tenants.id`).
source_draft: D-REQ-021
ssot_status: published
sot: Develop@a8a1edd713d6db6db61d42ed4eacf6a9e8737d07
<<<
RELATIONS:
- TYPE: Parent
  VALUE: USR-VAL-006

[REQUIREMENT]
UID: REQ-VAL-022
STATUS: Active
TITLE: REQ-VAL-022: `GET /api/tenants/mine` lists visible onboarded tenants for the user plus onboar
STATEMENT: >>>
`GET /api/tenants/mine` lists visible onboarded tenants for the user plus onboardable Manage-Server guilds.
<<<
COMMENT: >>>
domain: Tenant/Workspace
priority: must
type: system
constraints: Live Develop behavior only; Do not import Firebase Requirements.md wording
acceptance_criteria: `GET /api/tenants/mine` lists visible onboarded tenants for the user plus onboardable Manage-Server guilds.
source_draft: D-REQ-022
ssot_status: published
sot: Develop@a8a1edd713d6db6db61d42ed4eacf6a9e8737d07
<<<
RELATIONS:
- TYPE: Parent
  VALUE: USR-VAL-007

[REQUIREMENT]
UID: REQ-VAL-023
STATUS: Active
TITLE: REQ-VAL-023: When platform capacity is full, `onboardable` list is empty and billing capacity
STATEMENT: >>>
When platform capacity is full, `onboardable` list is empty and billing capacity flags are returned.
<<<
COMMENT: >>>
domain: Tenant/Workspace
priority: must
type: system
constraints: Live Develop behavior only; Do not import Firebase Requirements.md wording
acceptance_criteria: When platform capacity is full, `onboardable` list is empty and billing capacity flags are returned.
source_draft: D-REQ-023
ssot_status: published
sot: Develop@a8a1edd713d6db6db61d42ed4eacf6a9e8737d07
<<<
RELATIONS:
- TYPE: Parent
  VALUE: USR-VAL-007

[REQUIREMENT]
UID: REQ-VAL-024
STATUS: Active
TITLE: REQ-VAL-024: `POST /api/tenants/select` requires membership visibility; builds session user w
STATEMENT: >>>
`POST /api/tenants/select` requires membership visibility; builds session user with officer flag, enabled games, subscriptionAllowed.
<<<
COMMENT: >>>
domain: Tenant/Workspace
priority: must
type: system
constraints: Live Develop behavior only; Do not import Firebase Requirements.md wording
acceptance_criteria: `POST /api/tenants/select` requires membership visibility; builds session user with officer flag, enabled games, subscriptionAllowed.
source_draft: D-REQ-024
ssot_status: published
sot: Develop@a8a1edd713d6db6db61d42ed4eacf6a9e8737d07
<<<
RELATIONS:
- TYPE: Parent
  VALUE: USR-VAL-007

[REQUIREMENT]
UID: REQ-VAL-025
STATUS: Active
TITLE: REQ-VAL-025: Selecting a tenant upserts `auction/members/{discordId}` displayName/roles/synce
STATEMENT: >>>
Selecting a tenant upserts `auction/members/{discordId}` displayName/roles/syncedAt.
<<<
COMMENT: >>>
domain: Tenant/Workspace
priority: must
type: system
constraints: Live Develop behavior only; Do not import Firebase Requirements.md wording
acceptance_criteria: Selecting a tenant upserts `auction/members/{discordId}` displayName/roles/syncedAt.
source_draft: D-REQ-025
ssot_status: published
sot: Develop@a8a1edd713d6db6db61d42ed4eacf6a9e8737d07
<<<
RELATIONS:
- TYPE: Parent
  VALUE: USR-VAL-007

[REQUIREMENT]
UID: REQ-VAL-026
STATUS: Active
TITLE: REQ-VAL-026: `POST /api/tenants/onboard` requires Manage Server (or owner), bot already in gu
STATEMENT: >>>
`POST /api/tenants/onboard` requires Manage Server (or owner), bot already in guild, ≥1 officer role name.
<<<
COMMENT: >>>
domain: Tenant/Workspace
priority: must
type: system
constraints: Live Develop behavior only; Do not import Firebase Requirements.md wording
acceptance_criteria: `POST /api/tenants/onboard` requires Manage Server (or owner), bot already in guild, ≥1 officer role name.
source_draft: D-REQ-026
ssot_status: published
sot: Develop@a8a1edd713d6db6db61d42ed4eacf6a9e8737d07
<<<
RELATIONS:
- TYPE: Parent
  VALUE: USR-VAL-008

[REQUIREMENT]
UID: REQ-VAL-027
STATUS: Active
TITLE: REQ-VAL-027: Onboard creates tenant + settings with empty Discord channel map and marks `onbo
STATEMENT: >>>
Onboard creates tenant + settings with empty Discord channel map and marks `onboarded=true`.
<<<
COMMENT: >>>
domain: Tenant/Workspace
priority: must
type: system
constraints: Live Develop behavior only; Do not import Firebase Requirements.md wording
acceptance_criteria: Onboard creates tenant + settings with empty Discord channel map and marks `onboarded=true`.
source_draft: D-REQ-027
ssot_status: published
sot: Develop@a8a1edd713d6db6db61d42ed4eacf6a9e8737d07
<<<
RELATIONS:
- TYPE: Parent
  VALUE: USR-VAL-008

[REQUIREMENT]
UID: REQ-VAL-028
STATUS: Active
TITLE: REQ-VAL-028: Onboard rejects if guild already onboarded (409).
STATEMENT: >>>
Onboard rejects if guild already onboarded (409).
<<<
COMMENT: >>>
domain: Tenant/Workspace
priority: must
type: system
constraints: Live Develop behavior only; Do not import Firebase Requirements.md wording
acceptance_criteria: Onboard rejects if guild already onboarded (409).
source_draft: D-REQ-028
ssot_status: published
sot: Develop@a8a1edd713d6db6db61d42ed4eacf6a9e8737d07
<<<
RELATIONS:
- TYPE: Parent
  VALUE: USR-VAL-008

[REQUIREMENT]
UID: REQ-VAL-029
STATUS: Active
TITLE: REQ-VAL-029: Onboard rejects if bot not in guild and returns invite URL (`bot_not_in_guild`).
STATEMENT: >>>
Onboard rejects if bot not in guild and returns invite URL (`bot_not_in_guild`).
<<<
COMMENT: >>>
domain: Tenant/Workspace
priority: must
type: system
constraints: Live Develop behavior only; Do not import Firebase Requirements.md wording
acceptance_criteria: Onboard rejects if bot not in guild and returns invite URL (`bot_not_in_guild`).
source_draft: D-REQ-029
ssot_status: published
sot: Develop@a8a1edd713d6db6db61d42ed4eacf6a9e8737d07
<<<
RELATIONS:
- TYPE: Parent
  VALUE: USR-VAL-008

[REQUIREMENT]
UID: REQ-VAL-030
STATUS: Active
TITLE: REQ-VAL-030: `GET /api/tenants/invite-url` returns bot invite URL (optional `guildId` query).
STATEMENT: >>>
`GET /api/tenants/invite-url` returns bot invite URL (optional `guildId` query).
<<<
COMMENT: >>>
domain: Tenant/Workspace
priority: must
type: system
constraints: Live Develop behavior only; Do not import Firebase Requirements.md wording
acceptance_criteria: `GET /api/tenants/invite-url` returns bot invite URL (optional `guildId` query).
source_draft: D-REQ-030
ssot_status: published
sot: Develop@a8a1edd713d6db6db61d42ed4eacf6a9e8737d07
<<<
RELATIONS:
- TYPE: Parent
  VALUE: USR-VAL-008

[REQUIREMENT]
UID: REQ-VAL-031
STATUS: Active
TITLE: REQ-VAL-031: `GET /api/tenants/discord-roles` requires bot in guild; returns non-@everyone ro
STATEMENT: >>>
`GET /api/tenants/discord-roles` requires bot in guild; returns non-@everyone roles sorted by position.
<<<
COMMENT: >>>
domain: Tenant/Workspace
priority: must
type: system
constraints: Live Develop behavior only; Do not import Firebase Requirements.md wording
acceptance_criteria: `GET /api/tenants/discord-roles` requires bot in guild; returns non-@everyone roles sorted by position.
source_draft: D-REQ-031
ssot_status: published
sot: Develop@a8a1edd713d6db6db61d42ed4eacf6a9e8737d07
<<<
RELATIONS:
- TYPE: Parent
  VALUE: USR-VAL-008

[REQUIREMENT]
UID: REQ-VAL-032
STATUS: Active
TITLE: REQ-VAL-032: Officer = tenant `owner_discord_id` OR Discord role name/id listed in `adminRole
STATEMENT: >>>
Officer = tenant `owner_discord_id` OR Discord role name/id listed in `adminRoles` (case-insensitive); empty adminRoles → owner only.
<<<
COMMENT: >>>
domain: Tenant/Workspace
priority: must
type: system
constraints: Live Develop behavior only; Do not import Firebase Requirements.md wording
acceptance_criteria: Officer = tenant `owner_discord_id` OR Discord role name/id listed in `adminRoles` (case-insensitive); empty adminRoles → owner only.
source_draft: D-REQ-032
ssot_status: published
sot: Develop@a8a1edd713d6db6db61d42ed4eacf6a9e8737d07
<<<
RELATIONS:
- TYPE: Parent
  VALUE: USR-VAL-009

[REQUIREMENT]
UID: REQ-VAL-033
STATUS: Active
TITLE: REQ-VAL-033: Manage Server is required to create workspace, not for day-to-day officer tools.
STATEMENT: >>>
Manage Server is required to create workspace, not for day-to-day officer tools.
<<<
COMMENT: >>>
domain: Tenant/Workspace
priority: must
type: system
constraints: Live Develop behavior only; Do not import Firebase Requirements.md wording
acceptance_criteria: Manage Server is required to create workspace, not for day-to-day officer tools.
source_draft: D-REQ-033
ssot_status: published
sot: Develop@a8a1edd713d6db6db61d42ed4eacf6a9e8737d07
<<<
RELATIONS:
- TYPE: Parent
  VALUE: USR-VAL-009

[REQUIREMENT]
UID: REQ-VAL-034
STATUS: Active
TITLE: REQ-VAL-034: `GET/POST /api/tenants/workspace` officer-only; read/update display name, timezo
STATEMENT: >>>
`GET/POST /api/tenants/workspace` officer-only; read/update display name, timezone, adminRoles; returns Discord roles + invite URL.
<<<
COMMENT: >>>
domain: Tenant/Workspace
priority: must
type: system
constraints: Live Develop behavior only; Do not import Firebase Requirements.md wording
acceptance_criteria: `GET/POST /api/tenants/workspace` officer-only; read/update display name, timezone, adminRoles; returns Discord roles + invite URL.
source_draft: D-REQ-034
ssot_status: published
sot: Develop@a8a1edd713d6db6db61d42ed4eacf6a9e8737d07
<<<
RELATIONS:
- TYPE: Parent
  VALUE: USR-VAL-009

[REQUIREMENT]
UID: REQ-VAL-035
STATUS: Active
TITLE: REQ-VAL-035: Officers can upload guild logo (≤512KB) via `POST /api/tenants/logo` and clear v
STATEMENT: >>>
Officers can upload guild logo (≤512KB) via `POST /api/tenants/logo` and clear via `DELETE /api/tenants/logo`.
<<<
COMMENT: >>>
domain: Tenant/Workspace
priority: must
type: system
constraints: Live Develop behavior only; Do not import Firebase Requirements.md wording
acceptance_criteria: Officers can upload guild logo (≤512KB) via `POST /api/tenants/logo` and clear via `DELETE /api/tenants/logo`.
source_draft: D-REQ-035
ssot_status: published
sot: Develop@a8a1edd713d6db6db61d42ed4eacf6a9e8737d07
<<<
RELATIONS:
- TYPE: Parent
  VALUE: USR-VAL-009

[REQUIREMENT]
UID: REQ-VAL-036
STATUS: Active
TITLE: REQ-VAL-036: Effective logo falls back to Discord guild icon when no custom logo.
STATEMENT: >>>
Effective logo falls back to Discord guild icon when no custom logo.
<<<
COMMENT: >>>
domain: Tenant/Workspace
priority: must
type: system
constraints: Live Develop behavior only; Do not import Firebase Requirements.md wording
acceptance_criteria: Effective logo falls back to Discord guild icon when no custom logo.
source_draft: D-REQ-036
ssot_status: published
sot: Develop@a8a1edd713d6db6db61d42ed4eacf6a9e8737d07
<<<
RELATIONS:
- TYPE: Parent
  VALUE: USR-VAL-009

[REQUIREMENT]
UID: REQ-VAL-037
STATUS: Active
TITLE: REQ-VAL-037: Authenticated user without `currentTenantId` is forced to `/select-guild`.
STATEMENT: >>>
Authenticated user without `currentTenantId` is forced to `/select-guild`.
<<<
COMMENT: >>>
domain: Tenant/Workspace
priority: must
type: system
constraints: Live Develop behavior only; Do not import Firebase Requirements.md wording
acceptance_criteria: Authenticated user without `currentTenantId` is forced to `/select-guild`.
source_draft: D-REQ-037
ssot_status: published
sot: Develop@a8a1edd713d6db6db61d42ed4eacf6a9e8737d07
<<<
RELATIONS:
- TYPE: Parent
  VALUE: USR-VAL-010

[REQUIREMENT]
UID: REQ-VAL-038
STATUS: Active
TITLE: REQ-VAL-038: Post-login path resolver: select-guild → billing (if not allowed) → choose games
STATEMENT: >>>
Post-login path resolver: select-guild → billing (if not allowed) → choose games → game setup → game home.
<<<
COMMENT: >>>
domain: Tenant/Workspace
priority: must
type: system
constraints: Live Develop behavior only; Do not import Firebase Requirements.md wording
acceptance_criteria: Post-login path resolver: select-guild → billing (if not allowed) → choose games → game setup → game home.
source_draft: D-REQ-038
ssot_status: published
sot: Develop@a8a1edd713d6db6db61d42ed4eacf6a9e8737d07
<<<
RELATIONS:
- TYPE: Parent
  VALUE: USR-VAL-010

[[/SECTION]]

[[SECTION]]
TITLE: Games catalog (REQ-VAL-039 .. REQ-VAL-048)

[REQUIREMENT]
UID: REQ-VAL-039
STATUS: Active
TITLE: REQ-VAL-039: The known games are adventurer-guild, ragnarok-origin and ragnarok-3.
STATEMENT: >>>
The known games are adventurer-guild, ragnarok-origin and ragnarok-3.
<<<
COMMENT: >>>
domain: Games catalog
priority: must
type: system
constraints: Live Develop behavior only; Do not import Firebase Requirements.md wording
acceptance_criteria: The known games are adventurer-guild, ragnarok-origin and ragnarok-3.
source_draft: D-REQ-039
ssot_status: published
sot: xWhiteSpace/ROOGuildApp@f38e1378c7cca457fbf8de8e8355d59994f77fc8
<<<
RELATIONS:
- TYPE: Parent
  VALUE: USR-VAL-011

[REQUIREMENT]
UID: REQ-VAL-040
STATUS: Active
TITLE: REQ-VAL-040: `POST /api/tenants/enable-game` officer + active subscription; appends known gam
STATEMENT: >>>
`POST /api/tenants/enable-game` officer + active subscription; appends known game id.
<<<
COMMENT: >>>
domain: Games catalog
priority: must
type: system
constraints: Live Develop behavior only; Do not import Firebase Requirements.md wording
acceptance_criteria: `POST /api/tenants/enable-game` officer + active subscription; appends known game id.
source_draft: D-REQ-040
ssot_status: published
sot: Develop@a8a1edd713d6db6db61d42ed4eacf6a9e8737d07
<<<
RELATIONS:
- TYPE: Parent
  VALUE: USR-VAL-011

[REQUIREMENT]
UID: REQ-VAL-041
STATUS: Active
TITLE: REQ-VAL-041: `POST /api/tenants/disable-game` officer; removes game from enabled list without
STATEMENT: >>>
`POST /api/tenants/disable-game` officer; removes game from enabled list without deleting stored game data.
<<<
COMMENT: >>>
domain: Games catalog
priority: must
type: system
constraints: Live Develop behavior only; Do not import Firebase Requirements.md wording
acceptance_criteria: `POST /api/tenants/disable-game` officer; removes game from enabled list without deleting stored game data.
source_draft: D-REQ-041
ssot_status: published
sot: Develop@a8a1edd713d6db6db61d42ed4eacf6a9e8737d07
<<<
RELATIONS:
- TYPE: Parent
  VALUE: USR-VAL-011

[REQUIREMENT]
UID: REQ-VAL-042
STATUS: Active
TITLE: REQ-VAL-042: Ragnarok Origin setup incomplete until at least one of aucreq / auction / warAnn
STATEMENT: >>>
Ragnarok Origin setup incomplete until at least one of aucreq / auction / warAnnounce channel ids is mapped.
<<<
COMMENT: >>>
domain: Games catalog
priority: must
type: system
constraints: Live Develop behavior only; Do not import Firebase Requirements.md wording
acceptance_criteria: Ragnarok Origin setup incomplete until at least one of aucreq / auction / warAnnounce channel ids is mapped.
source_draft: D-REQ-042
ssot_status: published
sot: Develop@a8a1edd713d6db6db61d42ed4eacf6a9e8737d07
<<<
RELATIONS:
- TYPE: Parent
  VALUE: USR-VAL-012

[REQUIREMENT]
UID: REQ-VAL-043
STATUS: Active
TITLE: REQ-VAL-043: Adventurer Guild has no setup path / no channel requirements.
STATEMENT: >>>
Adventurer Guild has no setup path / no channel requirements.
<<<
COMMENT: >>>
domain: Games catalog
priority: must
type: system
constraints: Live Develop behavior only; Do not import Firebase Requirements.md wording
acceptance_criteria: Adventurer Guild has no setup path / no channel requirements.
source_draft: D-REQ-043
ssot_status: published
sot: Develop@a8a1edd713d6db6db61d42ed4eacf6a9e8737d07
<<<
RELATIONS:
- TYPE: Parent
  VALUE: USR-VAL-012

[REQUIREMENT]
UID: REQ-VAL-044
STATUS: Active
TITLE: REQ-VAL-044: `POST /api/tenants/game-setup` officer + RO enabled + active seat; persists Disc
STATEMENT: >>>
`POST /api/tenants/game-setup` officer + RO enabled + active seat; persists Discord channel map including war rooms 1–5.
<<<
COMMENT: >>>
domain: Games catalog
priority: must
type: system
constraints: Live Develop behavior only; Do not import Firebase Requirements.md wording
acceptance_criteria: `POST /api/tenants/game-setup` officer + RO enabled + active seat; persists Discord channel map including war rooms 1–5.
source_draft: D-REQ-044
ssot_status: published
sot: Develop@a8a1edd713d6db6db61d42ed4eacf6a9e8737d07
<<<
RELATIONS:
- TYPE: Parent
  VALUE: USR-VAL-012

[REQUIREMENT]
UID: REQ-VAL-045
STATUS: Active
TITLE: REQ-VAL-045: Mounted RO APIs require `requireGame(ragnarok-origin)` else 403 `game_required`.
STATEMENT: >>>
Mounted RO APIs require `requireGame(ragnarok-origin)` else 403 `game_required`.
<<<
COMMENT: >>>
domain: Games catalog
priority: must
type: system
constraints: Live Develop behavior only; Do not import Firebase Requirements.md wording
acceptance_criteria: Mounted RO APIs require `requireGame(ragnarok-origin)` else 403 `game_required`.
source_draft: D-REQ-045
ssot_status: published
sot: Develop@a8a1edd713d6db6db61d42ed4eacf6a9e8737d07
<<<
RELATIONS:
- TYPE: Parent
  VALUE: USR-VAL-012

[REQUIREMENT]
UID: REQ-VAL-046
STATUS: Active
TITLE: REQ-VAL-046: Mounted Adventurer Guild APIs require `requireGame(adventurer-guild)` else 403 `
STATEMENT: >>>
Mounted Adventurer Guild APIs require `requireGame(adventurer-guild)` else 403 `game_required`.
<<<
COMMENT: >>>
domain: Games catalog
priority: must
type: system
constraints: Live Develop behavior only; Do not import Firebase Requirements.md wording
acceptance_criteria: Mounted Adventurer Guild APIs require `requireGame(adventurer-guild)` else 403 `game_required`.
source_draft: D-REQ-046
ssot_status: published
sot: Develop@a8a1edd713d6db6db61d42ed4eacf6a9e8737d07
<<<
RELATIONS:
- TYPE: Parent
  VALUE: USR-VAL-012

[REQUIREMENT]
UID: REQ-VAL-047
STATUS: Active
TITLE: REQ-VAL-047: SPA blocks navigation into a game path that is not in `enabledGames` (redirect t
STATEMENT: >>>
SPA blocks navigation into a game path that is not in `enabledGames` (redirect to post-login path).
<<<
COMMENT: >>>
domain: Games catalog
priority: must
type: software
constraints: Live Develop behavior only; Do not import Firebase Requirements.md wording
acceptance_criteria: SPA blocks navigation into a game path that is not in `enabledGames` (redirect to post-login path).
source_draft: D-REQ-047
ssot_status: published
sot: Develop@a8a1edd713d6db6db61d42ed4eacf6a9e8737d07
<<<
RELATIONS:
- TYPE: Parent
  VALUE: USR-VAL-012

[REQUIREMENT]
UID: REQ-VAL-048
STATUS: Active
TITLE: REQ-VAL-048: Active game id persists in `localStorage` key `valhalla_active_game`.
STATEMENT: >>>
Active game id persists in `localStorage` key `valhalla_active_game`.
<<<
COMMENT: >>>
domain: Games catalog
priority: must
type: software
constraints: Live Develop behavior only; Do not import Firebase Requirements.md wording
acceptance_criteria: Active game id persists in `localStorage` key `valhalla_active_game`.
source_draft: D-REQ-048
ssot_status: published
sot: Develop@a8a1edd713d6db6db61d42ed4eacf6a9e8737d07
<<<
RELATIONS:
- TYPE: Parent
  VALUE: USR-VAL-012

[[/SECTION]]

[[SECTION]]
TITLE: Billing/Capacity (REQ-VAL-049 .. REQ-VAL-061)

[REQUIREMENT]
UID: REQ-VAL-049
STATUS: Active
TITLE: REQ-VAL-049: Tenant access (`tenantHasAccess`) when `subscription_status=active` OR (`past_du
STATEMENT: >>>
Tenant access (`tenantHasAccess`) when `subscription_status=active` OR (`past_due` with future `grace_until`).
<<<
COMMENT: >>>
domain: Billing/Capacity
priority: must
type: system
constraints: Live Develop behavior only; Do not import Firebase Requirements.md wording
acceptance_criteria: Tenant access (`tenantHasAccess`) when `subscription_status=active` OR (`past_due` with future `grace_until`).
source_draft: D-REQ-049
ssot_status: published
sot: Develop@a8a1edd713d6db6db61d42ed4eacf6a9e8737d07
<<<
RELATIONS:
- TYPE: Parent
  VALUE: USR-VAL-013

[REQUIREMENT]
UID: REQ-VAL-050
STATUS: Active
TITLE: REQ-VAL-050: Game feature mounts also require `requireActiveSubscription` → 402 `payment_requ
STATEMENT: >>>
Game feature mounts also require `requireActiveSubscription` → 402 `payment_required` when seat inactive.
<<<
COMMENT: >>>
domain: Billing/Capacity
priority: must
type: system
constraints: Live Develop behavior only; Do not import Firebase Requirements.md wording
acceptance_criteria: Game feature mounts also require `requireActiveSubscription` → 402 `payment_required` when seat inactive.
source_draft: D-REQ-050
ssot_status: published
sot: Develop@a8a1edd713d6db6db61d42ed4eacf6a9e8737d07
<<<
RELATIONS:
- TYPE: Parent
  VALUE: USR-VAL-013

[REQUIREMENT]
UID: REQ-VAL-051
STATUS: Active
TITLE: REQ-VAL-051: SPA redirects to `/workspace/billing` when `subscriptionAllowed===false` (except
STATEMENT: >>>
SPA redirects to `/workspace/billing` when `subscriptionAllowed===false` (except onboard/select/billing).
<<<
COMMENT: >>>
domain: Billing/Capacity
priority: must
type: software
constraints: Live Develop behavior only; Do not import Firebase Requirements.md wording
acceptance_criteria: SPA redirects to `/workspace/billing` when `subscriptionAllowed===false` (except onboard/select/billing).
source_draft: D-REQ-051
ssot_status: published
sot: Develop@a8a1edd713d6db6db61d42ed4eacf6a9e8737d07
<<<
RELATIONS:
- TYPE: Parent
  VALUE: USR-VAL-013

[REQUIREMENT]
UID: REQ-VAL-052
STATUS: Active
TITLE: REQ-VAL-052: `GET /api/billing/capacity` returns activeCount, cap (`BILLING_MAX_ACTIVE_GUILDS
STATEMENT: >>>
`GET /api/billing/capacity` returns activeCount, cap (`BILLING_MAX_ACTIVE_GUILDS`), full flag (public).
<<<
COMMENT: >>>
domain: Billing/Capacity
priority: must
type: system
constraints: Live Develop behavior only; Do not import Firebase Requirements.md wording
acceptance_criteria: `GET /api/billing/capacity` returns activeCount, cap (`BILLING_MAX_ACTIVE_GUILDS`), full flag (public).
source_draft: D-REQ-052
ssot_status: published
sot: Develop@a8a1edd713d6db6db61d42ed4eacf6a9e8737d07
<<<
RELATIONS:
- TYPE: Parent
  VALUE: USR-VAL-014

[REQUIREMENT]
UID: REQ-VAL-053
STATUS: Active
TITLE: REQ-VAL-053: `GET /api/billing/status` returns public billing view for current tenant (refres
STATEMENT: >>>
`GET /api/billing/status` returns public billing view for current tenant (refreshes Stripe when source=stripe).
<<<
COMMENT: >>>
domain: Billing/Capacity
priority: must
type: system
constraints: Live Develop behavior only; Do not import Firebase Requirements.md wording
acceptance_criteria: `GET /api/billing/status` returns public billing view for current tenant (refreshes Stripe when source=stripe).
source_draft: D-REQ-053
ssot_status: published
sot: Develop@a8a1edd713d6db6db61d42ed4eacf6a9e8737d07
<<<
RELATIONS:
- TYPE: Parent
  VALUE: USR-VAL-014

[REQUIREMENT]
UID: REQ-VAL-054
STATUS: Active
TITLE: REQ-VAL-054: Officer `POST /api/billing/create-checkout-session` creates Stripe subscription 
STATEMENT: >>>
Officer `POST /api/billing/create-checkout-session` creates Stripe subscription Checkout; rejects if already has access or capacity full.
<<<
COMMENT: >>>
domain: Billing/Capacity
priority: must
type: system
constraints: Live Develop behavior only; Do not import Firebase Requirements.md wording
acceptance_criteria: Officer `POST /api/billing/create-checkout-session` creates Stripe subscription Checkout; rejects if already has access or capacity full.
source_draft: D-REQ-054
ssot_status: published
sot: Develop@a8a1edd713d6db6db61d42ed4eacf6a9e8737d07
<<<
RELATIONS:
- TYPE: Parent
  VALUE: USR-VAL-015

[REQUIREMENT]
UID: REQ-VAL-055
STATUS: Active
TITLE: REQ-VAL-055: Officer `POST /api/billing/create-portal-session` opens Stripe Customer Portal w
STATEMENT: >>>
Officer `POST /api/billing/create-portal-session` opens Stripe Customer Portal when stripe customer exists.
<<<
COMMENT: >>>
domain: Billing/Capacity
priority: must
type: system
constraints: Live Develop behavior only; Do not import Firebase Requirements.md wording
acceptance_criteria: Officer `POST /api/billing/create-portal-session` opens Stripe Customer Portal when stripe customer exists.
source_draft: D-REQ-055
ssot_status: published
sot: Develop@a8a1edd713d6db6db61d42ed4eacf6a9e8737d07
<<<
RELATIONS:
- TYPE: Parent
  VALUE: USR-VAL-015

[REQUIREMENT]
UID: REQ-VAL-056
STATUS: Active
TITLE: REQ-VAL-056: Officer `POST /api/billing/redeem-invite` activates seat with `billing_source=in
STATEMENT: >>>
Officer `POST /api/billing/redeem-invite` activates seat with `billing_source=invite` under advisory lock; marks invite code redeemed once.
<<<
COMMENT: >>>
domain: Billing/Capacity
priority: must
type: system
constraints: Live Develop behavior only; Do not import Firebase Requirements.md wording
acceptance_criteria: Officer `POST /api/billing/redeem-invite` activates seat with `billing_source=invite` under advisory lock; marks invite code redeemed once.
source_draft: D-REQ-056
ssot_status: published
sot: Develop@a8a1edd713d6db6db61d42ed4eacf6a9e8737d07
<<<
RELATIONS:
- TYPE: Parent
  VALUE: USR-VAL-015

[REQUIREMENT]
UID: REQ-VAL-057
STATUS: Active
TITLE: REQ-VAL-057: Stripe webhook on `POST /api/billing/webhook` (raw body) handles checkout comple
STATEMENT: >>>
Stripe webhook on `POST /api/billing/webhook` (raw body) handles checkout completed, invoice paid/failed, subscription updated/deleted.
<<<
COMMENT: >>>
domain: Billing/Capacity
priority: must
type: system
constraints: Live Develop behavior only; Do not import Firebase Requirements.md wording
acceptance_criteria: Stripe webhook on `POST /api/billing/webhook` (raw body) handles checkout completed, invoice paid/failed, subscription updated/deleted.
source_draft: D-REQ-057
ssot_status: published
sot: Develop@a8a1edd713d6db6db61d42ed4eacf6a9e8737d07
<<<
RELATIONS:
- TYPE: Parent
  VALUE: USR-VAL-016

[REQUIREMENT]
UID: REQ-VAL-058
STATUS: Active
TITLE: REQ-VAL-058: Overflow checkout after capacity is canceled and refunded (rejectOverflowCheckou
STATEMENT: >>>
Overflow checkout after capacity is canceled and refunded (rejectOverflowCheckout).
<<<
COMMENT: >>>
domain: Billing/Capacity
priority: must
type: system
constraints: Live Develop behavior only; Do not import Firebase Requirements.md wording
acceptance_criteria: Overflow checkout after capacity is canceled and refunded (rejectOverflowCheckout).
source_draft: D-REQ-058
ssot_status: published
sot: Develop@a8a1edd713d6db6db61d42ed4eacf6a9e8737d07
<<<
RELATIONS:
- TYPE: Parent
  VALUE: USR-VAL-016

[REQUIREMENT]
UID: REQ-VAL-059
STATUS: Active
TITLE: REQ-VAL-059: Invoice payment failed sets `past_due` and grace window (`BILLING_PAST_DUE_GRACE
STATEMENT: >>>
Invoice payment failed sets `past_due` and grace window (`BILLING_PAST_DUE_GRACE_DAYS`, default 3).
<<<
COMMENT: >>>
domain: Billing/Capacity
priority: must
type: system
constraints: Live Develop behavior only; Do not import Firebase Requirements.md wording
acceptance_criteria: Invoice payment failed sets `past_due` and grace window (`BILLING_PAST_DUE_GRACE_DAYS`, default 3).
source_draft: D-REQ-059
ssot_status: published
sot: Develop@a8a1edd713d6db6db61d42ed4eacf6a9e8737d07
<<<
RELATIONS:
- TYPE: Parent
  VALUE: USR-VAL-016

[REQUIREMENT]
UID: REQ-VAL-060
STATUS: Active
TITLE: REQ-VAL-060: Permanent billing sources `invite` and `grandfathered` are not overwritten by St
STATEMENT: >>>
Permanent billing sources `invite` and `grandfathered` are not overwritten by Stripe subscription lifecycle.
<<<
COMMENT: >>>
domain: Billing/Capacity
priority: must
type: system
constraints: Live Develop behavior only; Do not import Firebase Requirements.md wording
acceptance_criteria: Permanent billing sources `invite` and `grandfathered` are not overwritten by Stripe subscription lifecycle.
source_draft: D-REQ-060
ssot_status: published
sot: Develop@a8a1edd713d6db6db61d42ed4eacf6a9e8737d07
<<<
RELATIONS:
- TYPE: Parent
  VALUE: USR-VAL-016

[REQUIREMENT]
UID: REQ-VAL-061
STATUS: Active
TITLE: REQ-VAL-061: Stripe env optional at boot; invite redemption works without Stripe keys.
STATEMENT: >>>
Stripe env optional at boot; invite redemption works without Stripe keys.
<<<
COMMENT: >>>
domain: Billing/Capacity
priority: must
type: system
constraints: Live Develop behavior only; Do not import Firebase Requirements.md wording
acceptance_criteria: Stripe env optional at boot; invite redemption works without Stripe keys.
source_draft: D-REQ-061
ssot_status: published
sot: Develop@a8a1edd713d6db6db61d42ed4eacf6a9e8737d07
<<<
RELATIONS:
- TYPE: Parent
  VALUE: USR-VAL-016

[[/SECTION]]

[[SECTION]]
TITLE: Discord bot/Channels (REQ-VAL-062 .. REQ-VAL-077, REQ-VAL-190, REQ-VAL-194, REQ-VAL-197 .. REQ-VAL-201)

[REQUIREMENT]
UID: REQ-VAL-062
STATUS: Active
TITLE: REQ-VAL-062: Bot intents include Guilds, GuildMessages, MessageContent, GuildMembers, GuildVo
STATEMENT: >>>
Bot intents include Guilds, GuildMessages, MessageContent, GuildMembers, GuildVoiceStates.
<<<
COMMENT: >>>
domain: Discord bot/Channels
priority: must
type: system
constraints: Live Develop behavior only; Do not import Firebase Requirements.md wording
acceptance_criteria: Bot intents include Guilds, GuildMessages, MessageContent, GuildMembers, GuildVoiceStates.
source_draft: D-REQ-062
ssot_status: published
sot: Develop@a8a1edd713d6db6db61d42ed4eacf6a9e8737d07
<<<
RELATIONS:
- TYPE: Parent
  VALUE: USR-VAL-017

[REQUIREMENT]
UID: REQ-VAL-063
STATUS: Active
TITLE: REQ-VAL-063: Missing `DISCORD_BOT_TOKEN` is fatal for bot init.
STATEMENT: >>>
Missing `DISCORD_BOT_TOKEN` is fatal for bot init.
<<<
COMMENT: >>>
domain: Discord bot/Channels
priority: must
type: system
constraints: Live Develop behavior only; Do not import Firebase Requirements.md wording
acceptance_criteria: Missing `DISCORD_BOT_TOKEN` is fatal for bot init.
source_draft: D-REQ-063
ssot_status: published
sot: Develop@a8a1edd713d6db6db61d42ed4eacf6a9e8737d07
<<<
RELATIONS:
- TYPE: Parent
  VALUE: USR-VAL-017

[REQUIREMENT]
UID: REQ-VAL-064
STATUS: Active
TITLE: REQ-VAL-064: On ready, clear leftover guild slash commands for each onboarded tenant; slash i
STATEMENT: >>>
On ready, clear leftover guild slash commands for each onboarded tenant; slash invocations reply that commands were removed (use cards).
<<<
COMMENT: >>>
domain: Discord bot/Channels
priority: must
type: system
constraints: Live Develop behavior only; Do not import Firebase Requirements.md wording
acceptance_criteria: On ready, clear leftover guild slash commands for each onboarded tenant; slash invocations reply that commands were removed (use cards).
source_draft: D-REQ-064
ssot_status: published
sot: Develop@a8a1edd713d6db6db61d42ed4eacf6a9e8737d07
<<<
RELATIONS:
- TYPE: Parent
  VALUE: USR-VAL-017

[REQUIREMENT]
UID: REQ-VAL-065
STATUS: Active
TITLE: REQ-VAL-065: Interaction routing by customId prefixes: `attcard:`, `ocr:`, `partycard:`, `req
STATEMENT: >>>
Interaction routing by customId prefixes: `attcard:`, `ocr:`, `partycard:`, `reqcard:`, `onboard:`, auction claim panel ids — bypass general-room gate.
<<<
COMMENT: >>>
domain: Discord bot/Channels
priority: must
type: system
constraints: Live Develop behavior only; Do not import Firebase Requirements.md wording
acceptance_criteria: Interaction routing by customId prefixes: `attcard:`, `ocr:`, `partycard:`, `reqcard:`, `onboard:`, auction claim panel ids — bypass general-room gate.
source_draft: D-REQ-065
ssot_status: published
sot: Develop@a8a1edd713d6db6db61d42ed4eacf6a9e8737d07
<<<
RELATIONS:
- TYPE: Parent
  VALUE: USR-VAL-018

[REQUIREMENT]
UID: REQ-VAL-066
STATUS: Active
TITLE: REQ-VAL-066: Every 60 seconds, for each onboarded tenant the process still serves, the tick r
STATEMENT: >>>
Every 60 seconds, for each onboarded tenant the process still serves, the tick runs phase announces and raid event announces only when it is not the first tick after ready and the Discord 429 circuit is closed; then monthly leave-credit refresh and war-room automation (REQ-ROO-192). Automatic archiving of a live raid at its monitoring end time is required by REQ-ROO-144 and is not tied to this tick.
<<<
COMMENT: >>>
domain: Discord bot/Channels
priority: must
type: system
constraints: Live Develop behavior only; Do not import Firebase Requirements.md wording
acceptance_criteria: Every 60 seconds, for each onboarded tenant the process still serves, the tick runs phase announces and raid event announces only when it is not the first tick after ready and the Discord 429 circuit is closed; then monthly leave-credit refresh and war-room automation (REQ-ROO-192). Automatic archiving of a live raid at its monitoring end time is required by REQ-ROO-144 and is not tied to this tick. | The tick does not call closeExpiredDeadlines, refreshGvgReadinessBoard, or maybeAutoCommitAuction.
source_draft: D-REQ-066
ssot_status: published
sot: Develop@56261347f46af5fb72d96b653fd48e8fda273d5c
<<<
RELATIONS:
- TYPE: Parent
  VALUE: USR-VAL-018

[REQUIREMENT]
UID: REQ-VAL-067
STATUS: Active
TITLE: REQ-VAL-067: Discord REST 429 opens a circuit; enqueue/status helpers surface human-readable 
STATEMENT: >>>
Discord REST 429 opens a circuit; enqueue/status helpers surface human-readable until times.
<<<
COMMENT: >>>
domain: Discord bot/Channels
priority: must
type: system
constraints: Live Develop behavior only; Do not import Firebase Requirements.md wording
acceptance_criteria: Discord REST 429 opens a circuit; enqueue/status helpers surface human-readable until times.
source_draft: D-REQ-067
ssot_status: published
sot: Develop@a8a1edd713d6db6db61d42ed4eacf6a9e8737d07
<<<
RELATIONS:
- TYPE: Parent
  VALUE: USR-VAL-018

[REQUIREMENT]
UID: REQ-VAL-068
STATUS: Active
TITLE: REQ-VAL-068: Optional `PROXY_URL` / HTTP(S)_PROXY routes Discord HTTP through Undici ProxyAge
STATEMENT: >>>
Optional `PROXY_URL` / HTTP(S)_PROXY routes Discord HTTP through Undici ProxyAgent.
<<<
COMMENT: >>>
domain: Discord bot/Channels
priority: must
type: system
constraints: Live Develop behavior only; Do not import Firebase Requirements.md wording
acceptance_criteria: Optional `PROXY_URL` / HTTP(S)_PROXY routes Discord HTTP through Undici ProxyAgent.
source_draft: D-REQ-068
ssot_status: published
sot: Develop@a8a1edd713d6db6db61d42ed4eacf6a9e8737d07
<<<
RELATIONS:
- TYPE: Parent
  VALUE: USR-VAL-018

[REQUIREMENT]
UID: REQ-VAL-069
STATUS: Active
TITLE: REQ-VAL-069: Prefer IPv4 for Discord connections (dns ipv4first + Agent family 4).
STATEMENT: >>>
Prefer IPv4 for Discord connections (dns ipv4first + Agent family 4).
<<<
COMMENT: >>>
domain: Discord bot/Channels
priority: must
type: system
constraints: Live Develop behavior only; Do not import Firebase Requirements.md wording
acceptance_criteria: Prefer IPv4 for Discord connections (dns ipv4first + Agent family 4).
source_draft: D-REQ-069
ssot_status: published
sot: Develop@a8a1edd713d6db6db61d42ed4eacf6a9e8737d07
<<<
RELATIONS:
- TYPE: Parent
  VALUE: USR-VAL-018

[REQUIREMENT]
UID: REQ-VAL-070
STATUS: Active
TITLE: REQ-VAL-070: Officer `GET /api/deploy-auction-card` posts Request Card to mapped auction-requ
STATEMENT: >>>
Officer `GET /api/deploy-auction-card` posts Request Card to mapped auction-request channel.
<<<
COMMENT: >>>
domain: Discord bot/Channels
priority: must
type: system
constraints: Live Develop behavior only; Do not import Firebase Requirements.md wording
acceptance_criteria: Officer `GET /api/deploy-auction-card` posts Request Card to mapped auction-request channel.
source_draft: D-REQ-070
ssot_status: published
sot: Develop@a8a1edd713d6db6db61d42ed4eacf6a9e8737d07
<<<
RELATIONS:
- TYPE: Parent
  VALUE: USR-VAL-019

[REQUIREMENT]
UID: REQ-VAL-071
STATUS: Active
TITLE: REQ-VAL-071: Officer `GET /api/deploy-attendance-card` posts GVG readiness dashboard to war-a
STATEMENT: >>>
Officer `GET /api/deploy-attendance-card` posts GVG readiness dashboard to war-announce channel.
<<<
COMMENT: >>>
domain: Discord bot/Channels
priority: must
type: system
constraints: Live Develop behavior only; Do not import Firebase Requirements.md wording
acceptance_criteria: Officer `GET /api/deploy-attendance-card` posts GVG readiness dashboard to war-announce channel.
source_draft: D-REQ-071
ssot_status: published
sot: Develop@a8a1edd713d6db6db61d42ed4eacf6a9e8737d07
<<<
RELATIONS:
- TYPE: Parent
  VALUE: USR-VAL-019

[REQUIREMENT]
UID: REQ-VAL-072
STATUS: Active
TITLE: REQ-VAL-072: Officer `GET /api/deploy-party-card` posts party viewer card to war-announce cha
STATEMENT: >>>
Officer `GET /api/deploy-party-card` posts party viewer card to war-announce channel.
<<<
COMMENT: >>>
domain: Discord bot/Channels
priority: must
type: system
constraints: Live Develop behavior only; Do not import Firebase Requirements.md wording
acceptance_criteria: Officer `GET /api/deploy-party-card` posts party viewer card to war-announce channel.
source_draft: D-REQ-072
ssot_status: published
sot: Develop@a8a1edd713d6db6db61d42ed4eacf6a9e8737d07
<<<
RELATIONS:
- TYPE: Parent
  VALUE: USR-VAL-019

[REQUIREMENT]
UID: REQ-VAL-073
STATUS: Active
TITLE: REQ-VAL-073: Officer `GET /api/deploy-ocr-card` posts party OCR card to war-announce channel.
STATEMENT: >>>
Officer `GET /api/deploy-ocr-card` posts party OCR card to war-announce channel.
<<<
COMMENT: >>>
domain: Discord bot/Channels
priority: must
type: system
constraints: Live Develop behavior only; Do not import Firebase Requirements.md wording
acceptance_criteria: Officer `GET /api/deploy-ocr-card` posts party OCR card to war-announce channel.
source_draft: D-REQ-073
ssot_status: published
sot: Develop@a8a1edd713d6db6db61d42ed4eacf6a9e8737d07
<<<
RELATIONS:
- TYPE: Parent
  VALUE: USR-VAL-019

[REQUIREMENT]
UID: REQ-VAL-074
STATUS: Active
TITLE: REQ-VAL-074: Attendance deploy-* aliases for Settings Send UX
STATEMENT: >>>
Attendance deploy-* aliases for Settings Send UX
<<<
COMMENT: >>>
domain: Discord bot/Channels
priority: must
type: system
constraints: Live Develop behavior only; Do not import Firebase Requirements.md wording
acceptance_criteria: Officer deploy actions remain exposed under /api/attendance/deploy-* for Settings-style mounts: deploy-card (GVG readiness), deploy-party-card, deploy-ocr-card, and deploy-onboarding-card. | GET /api/attendance/deploy-onboarding-card performs the same Discord Onboarding hub deploy as GET /api/deploy-onboarding-card for an officer session.
source_draft: D-REQ-074
ssot_status: published
sot: Develop@9237b35321389ccfef3ca0768305caa8ba345152
<<<
RELATIONS:
- TYPE: Parent
  VALUE: USR-VAL-019

[REQUIREMENT]
UID: REQ-VAL-075
STATUS: Active
TITLE: REQ-VAL-075: Per-tenant Discord channel map storage
STATEMENT: >>>
Per-tenant Discord channel map storage
<<<
COMMENT: >>>
domain: Discord bot/Channels
priority: must
type: system
constraints: Live Develop behavior only; Do not import Firebase Requirements.md wording
acceptance_criteria: Channel IDs for a tenant live in tenant_settings.discord_channels JSON (and the tenant channel cache), including onboardingChannelId alongside existing fields such as aucreqChannelId, auctionChannelId, warAnnounceChannelId, genroomId, and warRooms. | Resolvers never fill empty mapped channel fields from process.env; an empty onboardingChannelId stays empty even when DISCORD_ONBOARDING_CHANNEL_ID is set in the process environment. | Officers can enter and persist the Onboarding hub channel id in Ragnarok Origin setup and in Game Settings Discord channel IDs. | Ragnarok Origin setup completeness still depends only on aucreqChannelId, auctionChannelId, or warAnnounceChannelId; onboardingChannelId alone does not complete setup.
source_draft: D-REQ-075
ssot_status: published
sot: Develop@9237b35321389ccfef3ca0768305caa8ba345152
<<<
RELATIONS:
- TYPE: Parent
  VALUE: USR-VAL-019

[REQUIREMENT]
UID: REQ-VAL-076
STATUS: Active
TITLE: REQ-VAL-076: `GET /api/debug/discord-ratelimit` returns bot health + rate-limit status withou
STATEMENT: >>>
`GET /api/debug/discord-ratelimit` returns bot health + rate-limit status without secrets.
<<<
COMMENT: >>>
domain: Discord bot/Channels
priority: must
type: system
constraints: Live Develop behavior only; Do not import Firebase Requirements.md wording
acceptance_criteria: `GET /api/debug/discord-ratelimit` returns bot health + rate-limit status without secrets.
source_draft: D-REQ-076
ssot_status: published
sot: Develop@a8a1edd713d6db6db61d42ed4eacf6a9e8737d07
<<<
RELATIONS:
- TYPE: Parent
  VALUE: USR-VAL-020

[REQUIREMENT]
UID: REQ-VAL-077
STATUS: Active
TITLE: REQ-VAL-077: `GET /auth/discord-members` returns cached Discord member nicknames (2 min TTL) 
STATEMENT: >>>
`GET /auth/discord-members` returns cached Discord member nicknames (2 min TTL) or Postgres roster fallback without REST-fetching 1000 members from Render IP.
<<<
COMMENT: >>>
domain: Discord bot/Channels
priority: must
type: system
constraints: Live Develop behavior only; Do not import Firebase Requirements.md wording
acceptance_criteria: `GET /auth/discord-members` returns cached Discord member nicknames (2 min TTL) or Postgres roster fallback without REST-fetching 1000 members from Render IP.
source_draft: D-REQ-077
ssot_status: published
sot: Develop@a8a1edd713d6db6db61d42ed4eacf6a9e8737d07
<<<
RELATIONS:
- TYPE: Parent
  VALUE: USR-VAL-020

[REQUIREMENT]
UID: REQ-VAL-194
STATUS: Active
TITLE: REQ-VAL-194: The minute loop reuses cached onboarded tenants and settings
STATEMENT: >>>
The minute loop reuses cached onboarded tenants and settings
<<<
COMMENT: >>>
domain: Discord bot/Channels
priority: unspecified
type: system
constraints: The onboarded-tenant list cache is cleared on tenant create, mark onboarded, billing activation, and the automatic founding-seat revert.; Per-tenant configuration and channel caches are reused only when both are already populated for that tenant.; Tenants without access are still skipped.
acceptance_criteria: A 60-second tick does not call listOnboardedTenants again while the in-process list cache is populated. | A tick does not call loadTenantSettings for a tenant whose configuration and channels are already cached. | Creating a tenant, marking one onboarded, or activating/reverting billing clears the list so the next tick reloads onboarded tenants.
source_draft: delta-2026-10-03/mints.json
ssot_status: published
sot: Develop@9b8e7ae9ca2f9ccf046c5b609cdda545ced6eae9
<<<
RELATIONS:
- TYPE: Parent
  VALUE: USR-VAL-018

[REQUIREMENT]
UID: REQ-VAL-197
STATUS: Active
TITLE: REQ-VAL-197: Public Onboarding hub lists five topic buttons
STATEMENT: >>>
Public Onboarding hub lists five topic buttons
<<<
COMMENT: >>>
domain: Discord bot/Channels
priority: unspecified
type: software
constraints: Hub embed title is Onboarding.; Topic button labels are Auction, GvG, General Chat, Website, and Message.; Button customIds are onboard:auction, onboard:gvg, onboard:general, onboard:website, and onboard:message.
acceptance_criteria: A deployed public Onboarding message shows title Onboarding and a welcome body that tells the member to pick a topic for a private explanation and jump. | The message has exactly five topic buttons labeled Auction, GvG, General Chat, Website, and Message with customIds onboard:auction, onboard:gvg, onboard:general, onboard:website, and onboard:message. | Those five buttons are not link-style buttons on the hub itself.
source_draft: discord-onboarding-2026-10-05/mints.json
ssot_status: published
sot: Develop@9237b35321389ccfef3ca0768305caa8ba345152
<<<
RELATIONS:
- TYPE: Parent
  VALUE: USR-VAL-043

[REQUIREMENT]
UID: REQ-VAL-198
STATUS: Active
TITLE: REQ-VAL-198: Onboarding topic cards explain purpose and jump to mapped places
STATEMENT: >>>
Onboarding topic cards explain purpose and jump to mapped places
<<<
COMMENT: >>>
domain: Discord bot/Channels
priority: unspecified
type: software
constraints: Auction topic resolves aucreqChannelId; GvG resolves warAnnounceChannelId; General Chat resolves genroomId; Message resolves messageChannelId.; Website topic has no Discord channel field; jump uses the VALHALLA frontend origin with a trailing slash removed.; Purpose text and the hub welcome come from game settings discordCardCopy when that sentence is non-blank; blank or missing text uses the built-in default sentence.; Unmapped sentence when the topic channel id is empty: This channel is not mapped yet. Ask an officer to paste the ID in Settings.; Back control customId is onboard:back.
acceptance_criteria: Pressing Auction, GvG, General Chat, or Message on the hub yields a private topic card whose title matches the topic and whose body includes that topic's purpose text. | When the mapped channel id for that topic is set, the body mentions the channel and the card offers a Jump to channel link to discord.com/channels/{guildId}/{channelId} plus Back. | When that mapped channel id is empty, the body includes the unmapped Settings sentence, there is no jump link, and Back is present. | Pressing Website yields a topic card with the website purpose; when a frontend origin is configured it offers Open VALHALLA to that origin; when the origin is empty there is no Open VALHALLA link; Back is always present. | A saved discordCardCopy sentence replaces the default purpose text on that topic card. | Pressing Back from a topic card restores the public hub payload (title Onboarding and the five topic buttons).
source_draft: discord-onboarding-2026-10-05/mints.json
ssot_status: published
sot: Develop@9237b35321389ccfef3ca0768305caa8ba345152
<<<
RELATIONS:
- TYPE: Parent
  VALUE: USR-VAL-043

[REQUIREMENT]
UID: REQ-VAL-199
STATUS: Active
TITLE: REQ-VAL-199: Onboarding button ACK is ephemeral reply from the public hub and update when alr
STATEMENT: >>>
Onboarding button ACK is ephemeral reply from the public hub and update when already private
<<<
COMMENT: >>>
domain: Discord bot/Channels
priority: unspecified
type: system
constraints: Gateway routes interaction customIds that start with onboard:.; Public hub means the interaction is not already on an ephemeral message.; Unknown onboard customIds are ignored (no ACK class).
acceptance_criteria: From the public hub, a known topic button is acknowledged with an ephemeral defer-reply, then the reply is edited to that topic card. | From an already-ephemeral onboarding message, a topic button or Back is acknowledged with defer-update, then the same message is edited to the topic or hub. | Back from a topic returns the hub content in place without posting a new public hub message.
source_draft: discord-onboarding-2026-10-05/mints.json
ssot_status: published
sot: Develop@9237b35321389ccfef3ca0768305caa8ba345152
<<<
RELATIONS:
- TYPE: Parent
  VALUE: USR-VAL-043

[REQUIREMENT]
UID: REQ-VAL-190
STATUS: Active
TITLE: REQ-VAL-190: Phase-1 GEN get-ready line names the war date and jumps to GvG when mapped
STATEMENT: >>>
A due GvG Preparation announcement minute posts to GEN: Get ready for the next GVG on **{Mon DD, YYYY}**. Please Update your Job, or IGN on our System if you have change in-game. Thank you. When `warAnnounceChannelId` is mapped, the same message appends ` Jump in at <#id>.` When unmapped, that jump clause is omitted. The line has no event title and no war start time.
<<<
COMMENT: >>>
domain: Discord bot/Channels
priority: must
type: system
constraints: Live Develop behavior only; Do not import Firebase Requirements.md wording
acceptance_criteria: A due GvG Preparation announcement minute posts to GEN: Get ready for the next GVG on **{Mon DD, YYYY}**. Please Update your Job, or IGN on our System if you have change in-game. Thank you. When `warAnnounceChannelId` is mapped, the same message appends ` Jump in at <#id>.` When unmapped, that jump clause is omitted. The line has no event title and no war start time.
ssot_status: published
<<<
RELATIONS:
- TYPE: Parent
  VALUE: USR-VAL-018

[REQUIREMENT]
UID: REQ-VAL-200
STATUS: Active
TITLE: REQ-VAL-200: Onboarding hub redeploy edits the stored message when possible
STATEMENT: >>>
Onboarding hub redeploy edits the stored message when possible
<<<
COMMENT: >>>
domain: Discord bot/Channels
priority: unspecified
type: system
constraints: Store path is attendance/onboarding_card.; Stored fields are channelId, messageId, and updatedAt.; Edit is attempted only when stored channelId equals the target channel id and messageId is present.
acceptance_criteria: After a successful send or edit of the hub, the tenant store writes attendance/onboarding_card with that channelId, messageId, and an updatedAt timestamp. | A later deploy to the same channel edits the stored message's hub payload when Discord still has that message, and refreshes the pointer without requiring a new public message. | If the stored message cannot be fetched or edited, deploy sends a new hub message and updates the pointer to the new messageId.
source_draft: discord-onboarding-2026-10-05/mints.json
ssot_status: published
sot: Develop@9237b35321389ccfef3ca0768305caa8ba345152
<<<
RELATIONS:
- TYPE: Parent
  VALUE: USR-VAL-043

[REQUIREMENT]
UID: REQ-VAL-201
STATUS: Active
TITLE: REQ-VAL-201: Officer deploys the Onboarding hub to the mapped onboarding channel
STATEMENT: >>>
Officer deploys the Onboarding hub to the mapped onboarding channel
<<<
COMMENT: >>>
domain: Discord bot/Channels
priority: unspecified
type: system
constraints: Root route is GET /api/deploy-onboarding-card; Settings Send uses that root route.; Alias route is GET /api/attendance/deploy-onboarding-card.; Target channel is the tenant onboardingChannelId resolved via the DISCORD_ONBOARDING_CHANNEL_ID alias (tenant map only).; Live HTTP handlers do not call evaluateDeployOnboardingGate; they use officer checks plus deployPublicOnboardingCard error mapping.
acceptance_criteria: An authenticated officer calling GET /api/deploy-onboarding-card posts or edits the Onboarding hub in the tenant's mapped onboarding channel and returns success. | GET /api/attendance/deploy-onboarding-card performs the same Discord deploy for an officer and returns a JSON success envelope with the deploy result. | Unauthenticated callers receive 401; authenticated non-officers receive 403. | Empty onboarding channel mapping yields 400 without posting. | Bot not ready or Discord circuit/IP block yields 503 without posting. | Mapped id that the gateway cannot locate yields 404 without posting. | Game Settings shows an Onboarding Send control that triggers the root deploy route.
source_draft: discord-onboarding-2026-10-05/mints.json
ssot_status: published
sot: Develop@9237b35321389ccfef3ca0768305caa8ba345152
<<<
RELATIONS:
- TYPE: Parent
  VALUE: USR-VAL-019

[[/SECTION]]

[[SECTION]]
TITLE: Auction/Requests (REQ-ROO-078 .. REQ-ROO-100, REQ-ROO-174, REQ-ROO-179 .. REQ-ROO-181, REQ-ROO-185)

[REQUIREMENT]
UID: REQ-ROO-078
STATUS: Active
TITLE: REQ-ROO-078: `GET /api/requests/init` builds request lobby for signed-in member (gate/items/s
STATEMENT: >>>
`GET /api/requests/init` builds request lobby for signed-in member (gate/items/selections).
<<<
COMMENT: >>>
domain: Auction/Requests
priority: must
type: system
constraints: Live Develop behavior only; Do not import Firebase Requirements.md wording
acceptance_criteria: `GET /api/requests/init` builds request lobby for signed-in member (gate/items/selections).
source_draft: D-REQ-078
ssot_status: published
sot: Develop@a8a1edd713d6db6db61d42ed4eacf6a9e8737d07
<<<
RELATIONS:
- TYPE: Parent
  VALUE: USR-ROO-021

[REQUIREMENT]
UID: REQ-ROO-079
STATUS: Active
TITLE: REQ-ROO-079: `POST /api/requests/submit` accepts selections while registration gate open; ret
STATEMENT: >>>
`POST /api/requests/submit` accepts selections while registration gate open; returns RequestDeckError statuses.
<<<
COMMENT: >>>
domain: Auction/Requests
priority: must
type: system
constraints: Live Develop behavior only; Do not import Firebase Requirements.md wording
acceptance_criteria: `POST /api/requests/submit` accepts selections while registration gate open; returns RequestDeckError statuses.
source_draft: D-REQ-079
ssot_status: published
sot: Develop@a8a1edd713d6db6db61d42ed4eacf6a9e8737d07
<<<
RELATIONS:
- TYPE: Parent
  VALUE: USR-ROO-021

[REQUIREMENT]
UID: REQ-ROO-080
STATUS: Active
TITLE: REQ-ROO-080: `POST /api/requests/cancel` cancels pending request for item when allowed by dec
STATEMENT: >>>
`POST /api/requests/cancel` cancels pending request for item when allowed by deck rules.
<<<
COMMENT: >>>
domain: Auction/Requests
priority: must
type: system
constraints: Live Develop behavior only; Do not import Firebase Requirements.md wording
acceptance_criteria: `POST /api/requests/cancel` cancels pending request for item when allowed by deck rules.
source_draft: D-REQ-080
ssot_status: published
sot: Develop@a8a1edd713d6db6db61d42ed4eacf6a9e8737d07
<<<
RELATIONS:
- TYPE: Parent
  VALUE: USR-ROO-021

[REQUIREMENT]
UID: REQ-ROO-081
STATUS: Active
TITLE: REQ-ROO-081: Discord Request Card (`reqcard:*`) supports open/submit/drop without website (De
STATEMENT: >>>
Discord Request Card (`reqcard:*`) supports open/submit/drop without website (Develop tip).
<<<
COMMENT: >>>
domain: Auction/Requests
priority: must
type: system
constraints: Live Develop behavior only; Do not import Firebase Requirements.md wording
acceptance_criteria: Discord Request Card (`reqcard:*`) supports open/submit/drop without website (Develop tip).
source_draft: D-REQ-081
ssot_status: published
sot: Develop@a8a1edd713d6db6db61d42ed4eacf6a9e8737d07
<<<
RELATIONS:
- TYPE: Parent
  VALUE: USR-ROO-021

[REQUIREMENT]
UID: REQ-ROO-082
STATUS: Active
TITLE: REQ-ROO-082: Interactive auction claim panel updates `auction/active_session` when Discord ga
STATEMENT: >>>
Interactive auction claim panel updates `auction/active_session` when Discord gate open and member on roster.
<<<
COMMENT: >>>
domain: Auction/Requests
priority: must
type: system
constraints: Live Develop behavior only; Do not import Firebase Requirements.md wording
acceptance_criteria: Interactive auction claim panel updates `auction/active_session` when Discord gate open and member on roster.
source_draft: D-REQ-082
ssot_status: published
sot: Develop@a8a1edd713d6db6db61d42ed4eacf6a9e8737d07
<<<
RELATIONS:
- TYPE: Parent
  VALUE: USR-ROO-022

[REQUIREMENT]
UID: REQ-ROO-083
STATUS: Active
TITLE: REQ-ROO-083: Returns the active Mimic Book session with a names list for slot holders; resets
STATEMENT: >>>
Returns the active Mimic Book session with a names list for slot holders; resets if older than 24h, with an empty names list; the stored session never gets the names list.
<<<
COMMENT: >>>
domain: Auction/Requests
priority: must
type: system
constraints: Live Develop behavior only; Do not import Firebase Requirements.md wording
acceptance_criteria: Returns the active Mimic Book session with a names list for slot holders; resets if older than 24h, with an empty names list; the stored session never gets the names list.
source_draft: D-REQ-083
ssot_status: published
sot: xWhiteSpace/ROOGuildApp@f38e1378c7cca457fbf8de8e8355d59994f77fc8
<<<
RELATIONS:
- TYPE: Parent
  VALUE: USR-ROO-022

[REQUIREMENT]
UID: REQ-ROO-084
STATUS: Active
TITLE: REQ-ROO-084: Officer `POST /api/requests/update-session` writes active session with optimisti
STATEMENT: >>>
Officer `POST /api/requests/update-session` writes active session with optimistic version check (stale version aborted).
<<<
COMMENT: >>>
domain: Auction/Requests
priority: must
type: system
constraints: Live Develop behavior only; Do not import Firebase Requirements.md wording
acceptance_criteria: Officer `POST /api/requests/update-session` writes active session with optimistic version check (stale version aborted).
source_draft: D-REQ-084
ssot_status: published
sot: Develop@a8a1edd713d6db6db61d42ed4eacf6a9e8737d07
<<<
RELATIONS:
- TYPE: Parent
  VALUE: USR-ROO-022

[REQUIREMENT]
UID: REQ-ROO-085
STATUS: Active
TITLE: REQ-ROO-085: Officer `POST /api/requests/commit-session` atomically writes loot_history + pas
STATEMENT: >>>
Officer `POST /api/requests/commit-session` atomically writes loot_history + past_auctions + web_request status flips and clears active_session.
<<<
COMMENT: >>>
domain: Auction/Requests
priority: must
type: system
constraints: Live Develop behavior only; Do not import Firebase Requirements.md wording
acceptance_criteria: Officer `POST /api/requests/commit-session` atomically writes loot_history + past_auctions + web_request status flips and clears active_session.
source_draft: D-REQ-085
ssot_status: published
sot: Develop@a8a1edd713d6db6db61d42ed4eacf6a9e8737d07
<<<
RELATIONS:
- TYPE: Parent
  VALUE: USR-ROO-022

[REQUIREMENT]
UID: REQ-ROO-086
STATUS: Active
TITLE: REQ-ROO-086: Commit marks winners Selected, absent Absent, notSelected NotSelected; supersede
STATEMENT: >>>
Commit marks winners Selected, absent Absent, notSelected NotSelected; supersedes redundant pending rows.
<<<
COMMENT: >>>
domain: Auction/Requests
priority: must
type: system
constraints: Live Develop behavior only; Do not import Firebase Requirements.md wording
acceptance_criteria: Commit marks winners Selected, absent Absent, notSelected NotSelected; supersedes redundant pending rows.
source_draft: D-REQ-086
ssot_status: published
sot: Develop@a8a1edd713d6db6db61d42ed4eacf6a9e8737d07
<<<
RELATIONS:
- TYPE: Parent
  VALUE: USR-ROO-022

[REQUIREMENT]
UID: REQ-ROO-087
STATUS: Active
TITLE: REQ-ROO-087: Auto-commit scheduler can call the same `performCommitSession` path as manual co
STATEMENT: >>>
Auto-commit scheduler can call the same `performCommitSession` path as manual commit.
<<<
COMMENT: >>>
domain: Auction/Requests
priority: must
type: system
constraints: Live Develop behavior only; Do not import Firebase Requirements.md wording
acceptance_criteria: Auto-commit scheduler can call the same `performCommitSession` path as manual commit.
source_draft: D-REQ-087
ssot_status: published
sot: Develop@a8a1edd713d6db6db61d42ed4eacf6a9e8737d07
<<<
RELATIONS:
- TYPE: Parent
  VALUE: USR-ROO-022

[REQUIREMENT]
UID: REQ-ROO-088
STATUS: Active
TITLE: REQ-ROO-088: Officer `POST /api/requests/sync-roster` syncs Discord members into `auction/mem
STATEMENT: >>>
Officer `POST /api/requests/sync-roster` syncs Discord members into `auction/members`, marks missing as Ghost, never Ghosts `dummy_*`.
<<<
COMMENT: >>>
domain: Auction/Requests
priority: must
type: system
constraints: Live Develop behavior only; Do not import Firebase Requirements.md wording
acceptance_criteria: Officer `POST /api/requests/sync-roster` syncs Discord members into `auction/members`, marks missing as Ghost, never Ghosts `dummy_*`.
source_draft: D-REQ-088
ssot_status: published
sot: Develop@a8a1edd713d6db6db61d42ed4eacf6a9e8737d07
<<<
RELATIONS:
- TYPE: Parent
  VALUE: USR-ROO-023

[REQUIREMENT]
UID: REQ-ROO-089
STATUS: Active
TITLE: REQ-ROO-089: Officer `POST /api/requests/reset-priority` inserts AdminReset/Reset ledger row 
STATEMENT: >>>
Officer `POST /api/requests/reset-priority` inserts AdminReset/Reset ledger row for member+item.
<<<
COMMENT: >>>
domain: Auction/Requests
priority: must
type: system
constraints: Live Develop behavior only; Do not import Firebase Requirements.md wording
acceptance_criteria: Officer `POST /api/requests/reset-priority` inserts AdminReset/Reset ledger row for member+item.
source_draft: D-REQ-089
ssot_status: published
sot: Develop@a8a1edd713d6db6db61d42ed4eacf6a9e8737d07
<<<
RELATIONS:
- TYPE: Parent
  VALUE: USR-ROO-023

[REQUIREMENT]
UID: REQ-ROO-090
STATUS: Active
TITLE: REQ-ROO-090: Officer `POST /api/requests/clear-history` deletes web_requests whose date falls
STATEMENT: >>>
Officer `POST /api/requests/clear-history` deletes web_requests whose date falls in inclusive range.
<<<
COMMENT: >>>
domain: Auction/Requests
priority: must
type: system
constraints: Live Develop behavior only; Do not import Firebase Requirements.md wording
acceptance_criteria: Officer `POST /api/requests/clear-history` deletes web_requests whose date falls in inclusive range.
source_draft: D-REQ-090
ssot_status: published
sot: Develop@a8a1edd713d6db6db61d42ed4eacf6a9e8737d07
<<<
RELATIONS:
- TYPE: Parent
  VALUE: USR-ROO-023

[REQUIREMENT]
UID: REQ-ROO-091
STATUS: Active
TITLE: REQ-ROO-091: GET /api/requests/request-history defaults to page 1 and limit 20, and returns h
STATEMENT: >>>
GET /api/requests/request-history defaults to page 1 and limit 20, and returns history, total, page, and limit. Limit is clamped to 1–10000.
<<<
COMMENT: >>>
domain: Auction/Requests
priority: must
type: system
constraints: Live Develop behavior only; Do not import Firebase Requirements.md wording
acceptance_criteria: GET /api/requests/request-history defaults to page 1 and limit 20, and returns history, total, page, and limit. Limit is clamped to 1–10000. | mine=1 or mine=true returns only the signed-in user's rows. status other than all filters selectionStatus case-insensitively. q matches member or item, case-insensitive. | export=1 returns page 1 with limit 10000. preview=1 returns history as an empty array and the total count. | startDate and endDate, when both parse and start is not after end, keep rows whose push id falls in that timestamp window. They do not filter by the calendar-day expression. | Default sort date orders by the parsed calendar day of data.date (YYYY-MM-DD or M/D/YYYY). Descending puts unparseable dates last; ascending puts them first. id is the tie-break in the same direction. | sort member, item, or priority orders by those fields instead.
source_draft: D-REQ-091
ssot_status: published
sot: Develop@e9b6b9e804ad5d5433784039d738a568ee7850ca
<<<
RELATIONS:
- TYPE: Parent
  VALUE: USR-ROO-023

[REQUIREMENT]
UID: REQ-ROO-092
STATUS: Active
TITLE: REQ-ROO-092: GET /api/requests/loot-history with no date returns dates, each { date, iso, cou
STATEMENT: >>>
GET /api/requests/loot-history with no date returns dates, each { date, iso, count }, sorted by iso descending. It does not return history rows.
<<<
COMMENT: >>>
domain: Auction/Requests
priority: must
type: system
constraints: Live Develop behavior only; Do not import Firebase Requirements.md wording
acceptance_criteria: GET /api/requests/loot-history with no date returns dates, each { date, iso, count }, sorted by iso descending. It does not return history rows. | GET with date returns that date plus history rows whose stored date equals the ISO form, the M/D/YYYY form, or the zero-padded MM/DD/YYYY form, ordered by id descending. | Each history row has id, date, event, item, itemId, quantity, max, and mem.
source_draft: D-REQ-092
ssot_status: published
sot: Develop@3a3169d9b50670c8e6f6e4c45a0472b6c36b2630
<<<
RELATIONS:
- TYPE: Parent
  VALUE: USR-ROO-023

[REQUIREMENT]
UID: REQ-ROO-093
STATUS: Active
TITLE: REQ-ROO-093: GET /api/requests/past-auctions with no date returns dates ({ date, iso, count }
STATEMENT: >>>
GET /api/requests/past-auctions with no date returns dates ({ date, iso, count }) sorted by iso descending, and does not return a members map.
<<<
COMMENT: >>>
domain: Auction/Requests
priority: must
type: system
constraints: Live Develop behavior only; Do not import Firebase Requirements.md wording
acceptance_criteria: GET /api/requests/past-auctions with no date returns dates ({ date, iso, count }) sorted by iso descending, and does not return a members map. | GET with date returns history for that night using the same ISO / M/D/YYYY / MM/DD/YYYY match as loot history, ordered by id descending, plus the date echo, and no members map.
source_draft: D-REQ-093
ssot_status: published
sot: Develop@3a3169d9b50670c8e6f6e4c45a0472b6c36b2630
<<<
RELATIONS:
- TYPE: Parent
  VALUE: USR-ROO-023

[REQUIREMENT]
UID: REQ-ROO-094
STATUS: Active
TITLE: REQ-ROO-094: `GET /api/requests/member-auction-stats` self-or-officer; returns battle count +
STATEMENT: >>>
`GET /api/requests/member-auction-stats` self-or-officer; returns battle count + award qty by item.
<<<
COMMENT: >>>
domain: Auction/Requests
priority: must
type: system
constraints: Live Develop behavior only; Do not import Firebase Requirements.md wording
acceptance_criteria: `GET /api/requests/member-auction-stats` self-or-officer; returns battle count + award qty by item.
source_draft: D-REQ-094
ssot_status: published
sot: Develop@a8a1edd713d6db6db61d42ed4eacf6a9e8737d07
<<<
RELATIONS:
- TYPE: Parent
  VALUE: USR-ROO-023

[REQUIREMENT]
UID: REQ-ROO-095
STATUS: Active
TITLE: REQ-ROO-095: Settings help URLs exposed to all members via `GET /api/requests/settings/help` 
STATEMENT: >>>
Settings help URLs exposed to all members via `GET /api/requests/settings/help` (no adminRoles/channels).
<<<
COMMENT: >>>
domain: Auction/Requests
priority: must
type: system
constraints: Live Develop behavior only; Do not import Firebase Requirements.md wording
acceptance_criteria: Settings help URLs exposed to all members via `GET /api/requests/settings/help` (no adminRoles/channels).
source_draft: D-REQ-095
ssot_status: published
sot: Develop@a8a1edd713d6db6db61d42ed4eacf6a9e8737d07
<<<
RELATIONS:
- TYPE: Parent
  VALUE: USR-ROO-024

[REQUIREMENT]
UID: REQ-ROO-096
STATUS: Active
TITLE: REQ-ROO-096: `GET /api/requests/settings/get` returns public view for non-officers; full conf
STATEMENT: >>>
`GET /api/requests/settings/get` returns public view for non-officers; full config + discordChannels for officers.
<<<
COMMENT: >>>
domain: Auction/Requests
priority: must
type: system
constraints: Live Develop behavior only; Do not import Firebase Requirements.md wording
acceptance_criteria: `GET /api/requests/settings/get` returns public view for non-officers; full config + discordChannels for officers.
source_draft: D-REQ-096
ssot_status: published
sot: Develop@a8a1edd713d6db6db61d42ed4eacf6a9e8737d07
<<<
RELATIONS:
- TYPE: Parent
  VALUE: USR-ROO-024

[REQUIREMENT]
UID: REQ-ROO-097
STATUS: Active
TITLE: REQ-ROO-097: Officer `POST /api/requests/settings/save` with `scope=workspace|game`; game sco
STATEMENT: >>>
Officer `POST /api/requests/settings/save` with `scope=workspace|game`; game scope rejects overlapping raid cycles.
<<<
COMMENT: >>>
domain: Auction/Requests
priority: must
type: system
constraints: Live Develop behavior only; Do not import Firebase Requirements.md wording
acceptance_criteria: Officer `POST /api/requests/settings/save` with `scope=workspace|game`; game scope rejects overlapping raid cycles.
source_draft: D-REQ-097
ssot_status: published
sot: Develop@a8a1edd713d6db6db61d42ed4eacf6a9e8737d07
<<<
RELATIONS:
- TYPE: Parent
  VALUE: USR-ROO-024

[REQUIREMENT]
UID: REQ-ROO-098
STATUS: Active
TITLE: REQ-ROO-098: Officer `POST /api/requests/settings/unlock` marks session settings unlocked and
STATEMENT: >>>
Officer `POST /api/requests/settings/unlock` marks session settings unlocked and returns signed officer user.
<<<
COMMENT: >>>
domain: Auction/Requests
priority: must
type: system
constraints: Live Develop behavior only; Do not import Firebase Requirements.md wording
acceptance_criteria: Officer `POST /api/requests/settings/unlock` marks session settings unlocked and returns signed officer user.
source_draft: D-REQ-098
ssot_status: published
sot: Develop@a8a1edd713d6db6db61d42ed4eacf6a9e8737d07
<<<
RELATIONS:
- TYPE: Parent
  VALUE: USR-ROO-024

[REQUIREMENT]
UID: REQ-ROO-099
STATUS: Active
TITLE: REQ-ROO-099: Auction SPA routes: `/` Request, `/mimic-book`, `/request-history`, `/past-aucti
STATEMENT: >>>
Auction SPA routes: `/` Request, `/mimic-book`, `/request-history`, `/past-auction`.
<<<
COMMENT: >>>
domain: Auction/Requests
priority: must
type: system
constraints: Live Develop behavior only; Do not import Firebase Requirements.md wording
acceptance_criteria: Auction SPA routes: `/` Request, `/mimic-book`, `/request-history`, `/past-auction`.
source_draft: D-REQ-099
ssot_status: published
sot: Develop@a8a1edd713d6db6db61d42ed4eacf6a9e8737d07
<<<
RELATIONS:
- TYPE: Parent
  VALUE: USR-ROO-024

[REQUIREMENT]
UID: REQ-ROO-100
STATUS: Active
TITLE: REQ-ROO-100: `/submit-evidence` redirects to `/` (placeholder removed).
STATEMENT: >>>
`/submit-evidence` redirects to `/` (placeholder removed).
<<<
COMMENT: >>>
domain: Auction/Requests
priority: must
type: system
constraints: Live Develop behavior only; Do not import Firebase Requirements.md wording
acceptance_criteria: `/submit-evidence` redirects to `/` (placeholder removed).
source_draft: D-REQ-100
ssot_status: published
sot: Develop@a8a1edd713d6db6db61d42ed4eacf6a9e8737d07
<<<
RELATIONS:
- TYPE: Parent
  VALUE: USR-ROO-024

[REQUIREMENT]
UID: REQ-ROO-174
STATUS: Active
TITLE: REQ-ROO-174: Request pity and lobby priority are scored by calendar day and reset after a win
STATEMENT: >>>
Request pity and lobby priority are scored by calendar day and reset after a win
<<<
COMMENT: >>>
domain: Auction/Requests
priority: unspecified
type: system
constraints: Calendar day is row.date if it parses, else row.eventDate. Accepted forms: YYYY-MM-DD and M/D/YYYY. Unparseable dates are ignored.; Lookback is priorityLookbackDays clamped to 1–365; unset uses 30. Inclusive window is today-(days-1) through today in the guild timezone. Days after today are excluded.; Order inside the window is calendar day, then write-time decoded from the row id, then the id string.; Selected and Reset end the streak. Absent ends it unless the item is high value. High-value Absent counts as one night and does not end the streak.; After the last ending row, each distinct calendar day of NotSelected counts 1. Pending, Superseded, and Canceled neither count nor end. The same night counts once.; Commit and reset-priority store eventDate as the ISO session date: parsed targetSessionDate, otherwise the guild calendar day.
acceptance_criteria: A Selected (or Reset, or non-high-value Absent) on a later calendar day than a NotSelected yields pity 0 for that member and item, even when the win row's id sorts before the loss id. | Two NotSelected rows on the same calendar day contribute 1, not 2. A Pending or Canceled row on another day contributes 0. | For a high-value item, an Absent night plus a later NotSelected night scores 2, and the Absent does not end the streak. For a non-high-value item the same rows score 1 (only the NotSelected after the Absent). | The request lobby, Mimic standings, Discord request snapshot, and auction auto-commit leaderboard show this live score on pending bids, not the priority number stored on the pending row. | A pending bid and a Selected row for the same member, item, and calendar day show priority 0. | Committed web_requests (Selected, NotSelected, Absent, Superseded) and an officer priority-reset row carry eventDate set to that ISO session date. | Request History renders eventDate when it is non-empty and '---' when it is empty.
source_draft: delta-2026-10-03/mints.json
ssot_status: published
sot: Develop@9b8e7ae9ca2f9ccf046c5b609cdda545ced6eae9
<<<
RELATIONS:
- TYPE: Parent
  VALUE: USR-ROO-023

[REQUIREMENT]
UID: REQ-ROO-179
STATUS: Active
TITLE: REQ-ROO-179: Review Allocation and the Live Auction announce are per-item rows
STATEMENT: >>>
Review Allocation and the Live Auction announce are per-item rows
<<<
COMMENT: >>>
domain: Auction/Requests
priority: unspecified
type: software
constraints: Only items with lootSummary qty > 0 are listed.; Selected rows are the unique non-empty uids in categoryAllocations[itemId].selected, ordered by rank then uid.; Not-selected rows are rankingsByItem[itemId] minus those uids, in ranking order.; Rank label is the 1-based index in that item's ranking, padded to 2 digits, or an em dash when the uid is not in the ranking.; Priority is the lobby detail priority, or 0 when missing. One row per item and member, not per loot slot.; Discord mentions snowflake uids; other uids are shown as display name. Messages chunk at 2000 characters.
acceptance_criteria: Review Allocation selected and not-selected tables have columns #, Item, Member, Priority, and do not have a Requested column. | The same member selected on two loot items appears twice, once per item, instead of once in a unique-member list. | An item with no loot qty does not appear. | The GEN-room Live Auction message lists those same rows as '#{rank}  **{item}**  {member}  Prio {n}' under the existing selected and not-selected sentences, not as mention columns of unique members.
source_draft: delta-2026-10-03/mints.json
ssot_status: published
sot: Develop@9b8e7ae9ca2f9ccf046c5b609cdda545ced6eae9
<<<
RELATIONS:
- TYPE: Parent
  VALUE: USR-ROO-022

[REQUIREMENT]
UID: REQ-ROO-180
STATUS: Active
TITLE: REQ-ROO-180: Confirm Allocate saves the session, then announces from the server
STATEMENT: >>>
Confirm Allocate saves the session, then announces from the server
<<<
COMMENT: >>>
domain: Auction/Requests
priority: unspecified
type: system
constraints: POST /api/requests/announce-allocate accepts no client winner list. Body may be empty.; Officer check uses configuration adminRoles via the Discord officer check. No session identity is 401. Non-officer is 403.; No active_session is 400 with error 'No active Mimic Book session.'; Discord 'not configured' is 400; offline, not connected, rate-limited, or temporarily blocking is 503; not found is 404.; Confirm writes activeStep 2, the preview loot summary, category allocations, initial winners, active matrix filter, and sidebarTab 'standby' before announcing.
acceptance_criteria: Confirm Allocate does not call the announce route when the session write fails, and the officer sees 'Session saved locally, but the server write failed. Discord announce skipped.' | When the session write succeeds, Confirm Allocate posts /api/requests/announce-allocate and the GEN-room message is built from the stored session plus the current request lobby (REQ-ROO-179 rows). | Announce Live Auction posts that same route without requiring the confirm-modal save. | While the announce is in flight the confirm button reads 'Allocating…' and is disabled.
source_draft: delta-2026-10-03/mints.json
ssot_status: published
sot: Develop@9b8e7ae9ca2f9ccf046c5b609cdda545ced6eae9
<<<
RELATIONS:
- TYPE: Parent
  VALUE: USR-ROO-022

[REQUIREMENT]
UID: REQ-ROO-181
STATUS: Active
TITLE: REQ-ROO-181: Mimic Book does not re-GET the session while the page stays open
STATEMENT: >>>
Mimic Book does not re-GET the session while the page stays open
<<<
COMMENT: >>>
domain: Auction/Requests
priority: unspecified
type: software
constraints: GET /api/requests/active-session ETag is 'empty' when no session exists, otherwise s:{version}:{lastUpdated}.; A matching If-None-Match returns 304 with an empty body and Cache-Control private, no-cache. The 24-hour auto-reset in REQ-ROO-083 still applies on a real GET.
acceptance_criteria: Leaving Mimic Book open does not issue a repeating GET of /api/requests/active-session. | The session is loaded when the signed-in user identity for the page changes. | A client that repeats the GET with the current ETag receives 304 and no session body.
source_draft: delta-2026-10-03/mints.json
ssot_status: published
sot: Develop@9b8e7ae9ca2f9ccf046c5b609cdda545ced6eae9
<<<
RELATIONS:
- TYPE: Parent
  VALUE: USR-ROO-022

[REQUIREMENT]
UID: REQ-ROO-185
STATUS: Active
TITLE: REQ-ROO-185: Settings GET can return an allow-listed field subset
STATEMENT: >>>
Settings GET can return an allow-listed field subset
<<<
COMMENT: >>>
domain: Auction/Requests
priority: unspecified
type: system
constraints: Allow-list: jobs, items, timezone, roles, events, specialEventCategories, expectedAttendanceRate, warRooms, liveRaidMaxWarRooms, liveRaidMaxConfigs, helpEmbedUrl, raidHelpEmbedUrl, guildDisplayName, guildLogoUrl, defaultLeaveCredits, isForceLocked.; Unknown names are dropped. Non-officers are still filtered through the public settings view before the pick.
acceptance_criteria: GET /api/requests/settings/get?fields=jobs,timezone returns success, needsSetup, publicOnly, and a config object that has only those requested allow-listed keys. | GET without fields still returns the full officer config plus discord channels, or the public view, as in REQ-ROO-096.
source_draft: delta-2026-10-03/mints.json
ssot_status: published
sot: Develop@9b8e7ae9ca2f9ccf046c5b609cdda545ced6eae9
<<<
RELATIONS:
- TYPE: Parent
  VALUE: USR-ROO-024

[[/SECTION]]

[[SECTION]]
TITLE: Attendance/Roster (REQ-ROO-101 .. REQ-ROO-113, REQ-ROO-173, REQ-ROO-187)

[REQUIREMENT]
UID: REQ-ROO-101
STATUS: Active
TITLE: REQ-ROO-101: Officer `POST /api/attendance/vanish` removes members from DB (batch ≤500) and k
STATEMENT: >>>
Officer `POST /api/attendance/vanish` removes members from DB (batch ≤500) and kicks non-dummy Discord members when possible.
<<<
COMMENT: >>>
domain: Attendance/Roster
priority: must
type: system
constraints: Live Develop behavior only; Do not import Firebase Requirements.md wording
acceptance_criteria: Officer `POST /api/attendance/vanish` removes members from DB (batch ≤500) and kicks non-dummy Discord members when possible.
source_draft: D-REQ-101
ssot_status: published
sot: Develop@a8a1edd713d6db6db61d42ed4eacf6a9e8737d07
<<<
RELATIONS:
- TYPE: Parent
  VALUE: USR-ROO-025

[REQUIREMENT]
UID: REQ-ROO-102
STATUS: Active
TITLE: REQ-ROO-102: Officer `POST /api/attendance/update-roster-status` atomically patches roster le
STATEMENT: >>>
Officer `POST /api/attendance/update-roster-status` atomically patches roster leaf fields.
<<<
COMMENT: >>>
domain: Attendance/Roster
priority: must
type: system
constraints: Live Develop behavior only; Do not import Firebase Requirements.md wording
acceptance_criteria: Officer `POST /api/attendance/update-roster-status` atomically patches roster leaf fields.
source_draft: D-REQ-102
ssot_status: published
sot: Develop@a8a1edd713d6db6db61d42ed4eacf6a9e8737d07
<<<
RELATIONS:
- TYPE: Parent
  VALUE: USR-ROO-025

[REQUIREMENT]
UID: REQ-ROO-103
STATUS: Active
TITLE: REQ-ROO-103: Officer `POST /api/attendance/roster/save-batch` bulk-persists roster leaf updat
STATEMENT: >>>
Officer `POST /api/attendance/roster/save-batch` bulk-persists roster leaf updates.
<<<
COMMENT: >>>
domain: Attendance/Roster
priority: must
type: system
constraints: Live Develop behavior only; Do not import Firebase Requirements.md wording
acceptance_criteria: Officer `POST /api/attendance/roster/save-batch` bulk-persists roster leaf updates.
source_draft: D-REQ-103
ssot_status: published
sot: Develop@a8a1edd713d6db6db61d42ed4eacf6a9e8737d07
<<<
RELATIONS:
- TYPE: Parent
  VALUE: USR-ROO-025

[REQUIREMENT]
UID: REQ-ROO-104
STATUS: Active
TITLE: REQ-ROO-104: Officer `POST /api/attendance/dummy/create` creates placeholder `dummy_*` roster
STATEMENT: >>>
Officer `POST /api/attendance/dummy/create` creates placeholder `dummy_*` roster members.
<<<
COMMENT: >>>
domain: Attendance/Roster
priority: must
type: system
constraints: Live Develop behavior only; Do not import Firebase Requirements.md wording
acceptance_criteria: Officer `POST /api/attendance/dummy/create` creates placeholder `dummy_*` roster members.
source_draft: D-REQ-104
ssot_status: published
sot: Develop@a8a1edd713d6db6db61d42ed4eacf6a9e8737d07
<<<
RELATIONS:
- TYPE: Parent
  VALUE: USR-ROO-025

[REQUIREMENT]
UID: REQ-ROO-105
STATUS: Active
TITLE: REQ-ROO-105: `GET /api/attendance/profile` / `GET /api/attendance/members/:uid/profile` retur
STATEMENT: >>>
`GET /api/attendance/profile` / `GET /api/attendance/members/:uid/profile` return member profile (self or targeted).
<<<
COMMENT: >>>
domain: Attendance/Roster
priority: must
type: system
constraints: Live Develop behavior only; Do not import Firebase Requirements.md wording
acceptance_criteria: `GET /api/attendance/profile` / `GET /api/attendance/members/:uid/profile` return member profile (self or targeted).
source_draft: D-REQ-105
ssot_status: published
sot: Develop@a8a1edd713d6db6db61d42ed4eacf6a9e8737d07
<<<
RELATIONS:
- TYPE: Parent
  VALUE: USR-ROO-026

[REQUIREMENT]
UID: REQ-ROO-106
STATUS: Active
TITLE: REQ-ROO-106: `GET /api/attendance/me` returns current user leave credits / no-confirm summary
STATEMENT: >>>
`GET /api/attendance/me` returns current user leave credits / no-confirm summary.
<<<
COMMENT: >>>
domain: Attendance/Roster
priority: must
type: system
constraints: Live Develop behavior only; Do not import Firebase Requirements.md wording
acceptance_criteria: `GET /api/attendance/me` returns current user leave credits / no-confirm summary.
source_draft: D-REQ-106
ssot_status: published
sot: Develop@a8a1edd713d6db6db61d42ed4eacf6a9e8737d07
<<<
RELATIONS:
- TYPE: Parent
  VALUE: USR-ROO-026

[REQUIREMENT]
UID: REQ-ROO-107
STATUS: Active
TITLE: REQ-ROO-107: Officer `POST /api/attendance/members/:uid/leave-credits` adjusts leave credits 
STATEMENT: >>>
Officer `POST /api/attendance/members/:uid/leave-credits` adjusts leave credits by delta.
<<<
COMMENT: >>>
domain: Attendance/Roster
priority: must
type: system
constraints: Live Develop behavior only; Do not import Firebase Requirements.md wording
acceptance_criteria: Officer `POST /api/attendance/members/:uid/leave-credits` adjusts leave credits by delta.
source_draft: D-REQ-107
ssot_status: published
sot: Develop@a8a1edd713d6db6db61d42ed4eacf6a9e8737d07
<<<
RELATIONS:
- TYPE: Parent
  VALUE: USR-ROO-026

[REQUIREMENT]
UID: REQ-ROO-108
STATUS: Active
TITLE: REQ-ROO-108: Boot seeds missing leave credits per onboarded tenant (`seedMissingLeaveCredits`
STATEMENT: >>>
Boot seeds missing leave credits per onboarded tenant (`seedMissingLeaveCredits`).
<<<
COMMENT: >>>
domain: Attendance/Roster
priority: must
type: system
constraints: Live Develop behavior only; Do not import Firebase Requirements.md wording
acceptance_criteria: Boot seeds missing leave credits per onboarded tenant (`seedMissingLeaveCredits`).
source_draft: D-REQ-108
ssot_status: published
sot: Develop@a8a1edd713d6db6db61d42ed4eacf6a9e8737d07
<<<
RELATIONS:
- TYPE: Parent
  VALUE: USR-ROO-026

[REQUIREMENT]
UID: REQ-ROO-109
STATUS: Active
TITLE: REQ-ROO-109: Monthly leave-credit refresh runs from bot ticker (`maybeRefreshMonthlyLeaveCred
STATEMENT: >>>
Monthly leave-credit refresh runs from bot ticker (`maybeRefreshMonthlyLeaveCredits`).
<<<
COMMENT: >>>
domain: Attendance/Roster
priority: must
type: system
constraints: Live Develop behavior only; Do not import Firebase Requirements.md wording
acceptance_criteria: Monthly leave-credit refresh runs from bot ticker (`maybeRefreshMonthlyLeaveCredits`).
source_draft: D-REQ-109
ssot_status: published
sot: Develop@a8a1edd713d6db6db61d42ed4eacf6a9e8737d07
<<<
RELATIONS:
- TYPE: Parent
  VALUE: USR-ROO-026

[REQUIREMENT]
UID: REQ-ROO-110
STATUS: Active
TITLE: REQ-ROO-110: `GET /api/attendance/peak-hours` aggregates guild peak-hour heatmap; `PUT /api/a
STATEMENT: >>>
`GET /api/attendance/peak-hours` aggregates guild peak-hour heatmap; `PUT /api/attendance/peak-hours/me` saves own play schedule.
<<<
COMMENT: >>>
domain: Attendance/Roster
priority: must
type: system
constraints: Live Develop behavior only; Do not import Firebase Requirements.md wording
acceptance_criteria: `GET /api/attendance/peak-hours` aggregates guild peak-hour heatmap; `PUT /api/attendance/peak-hours/me` saves own play schedule.
source_draft: D-REQ-110
ssot_status: published
sot: Develop@a8a1edd713d6db6db61d42ed4eacf6a9e8737d07
<<<
RELATIONS:
- TYPE: Parent
  VALUE: USR-ROO-027

[REQUIREMENT]
UID: REQ-ROO-111
STATUS: Active
TITLE: REQ-ROO-111: Officer `POST /api/attendance/update-job-target` saves recruitment goals by job.
STATEMENT: >>>
Officer `POST /api/attendance/update-job-target` saves recruitment goals by job.
<<<
COMMENT: >>>
domain: Attendance/Roster
priority: must
type: system
constraints: Live Develop behavior only; Do not import Firebase Requirements.md wording
acceptance_criteria: Officer `POST /api/attendance/update-job-target` saves recruitment goals by job.
source_draft: D-REQ-111
ssot_status: published
sot: Develop@a8a1edd713d6db6db61d42ed4eacf6a9e8737d07
<<<
RELATIONS:
- TYPE: Parent
  VALUE: USR-ROO-027

[REQUIREMENT]
UID: REQ-ROO-112
STATUS: Active
TITLE: REQ-ROO-112: Officer `POST /api/attendance/update-expected-rate` saves guild expected attenda
STATEMENT: >>>
Officer `POST /api/attendance/update-expected-rate` saves guild expected attendance rate.
<<<
COMMENT: >>>
domain: Attendance/Roster
priority: must
type: system
constraints: Live Develop behavior only; Do not import Firebase Requirements.md wording
acceptance_criteria: Officer `POST /api/attendance/update-expected-rate` saves guild expected attendance rate.
source_draft: D-REQ-112
ssot_status: published
sot: Develop@a8a1edd713d6db6db61d42ed4eacf6a9e8737d07
<<<
RELATIONS:
- TYPE: Parent
  VALUE: USR-ROO-027

[REQUIREMENT]
UID: REQ-ROO-113
STATUS: Active
TITLE: REQ-ROO-113: Frontend MasterList / Profile / Peak Hours / Statistics pages are mounted under 
STATEMENT: >>>
Frontend MasterList / Profile / Peak Hours / Statistics pages are mounted under `/attendance/*`.
<<<
COMMENT: >>>
domain: Attendance/Roster
priority: must
type: software
constraints: Live Develop behavior only; Do not import Firebase Requirements.md wording
acceptance_criteria: Frontend MasterList / Profile / Peak Hours / Statistics pages are mounted under `/attendance/*`.
source_draft: D-REQ-113
ssot_status: published
sot: Develop@a8a1edd713d6db6db61d42ed4eacf6a9e8737d07
<<<
RELATIONS:
- TYPE: Parent
  VALUE: USR-ROO-027

[REQUIREMENT]
UID: REQ-ROO-173
STATUS: Active
TITLE: REQ-ROO-173: Master List chevrons stay fixed when the slide title changes
STATEMENT: >>>
Master List chevrons stay fixed when the slide title changes
<<<
COMMENT: >>>
domain: Attendance/Roster
priority: unspecified
type: software
constraints: Roster sizer label uses the larger of the active raid-roster count and ROSTER_CAP (200 at this tip), not the live count alone.; Visible title truncates; invisible copies of every slide label occupy the same grid cell.
acceptance_criteria: On Master List, switching carousel slides does not move the previous/next chevrons horizontally. | The reserved title width is at least the widest slide label, and for the roster slide at least the label that would show if the active count were ROSTER_CAP. | The visible heading is the current slide title (roster heading includes the live active count and cap) and truncates instead of widening the chevron row.
source_draft: delta-2026-10-03/mints.json
ssot_status: published
sot: Develop@9b8e7ae9ca2f9ccf046c5b609cdda545ced6eae9
<<<
RELATIONS:
- TYPE: Parent
  VALUE: USR-ROO-027

[REQUIREMENT]
UID: REQ-ROO-187
STATUS: Active
TITLE: REQ-ROO-187: Card roster view omits unused member fields
STATEMENT: >>>
Card roster view omits unused member fields
<<<
COMMENT: >>>
domain: Attendance/Roster
priority: unspecified
type: system
constraints: Card fields are exactly uid, displayName, jobCode, and isRaidRoster (true only when the stored flag is true).
acceptance_criteria: GET /api/attendance/members?view=card returns one object per roster member containing only uid, displayName, jobCode, and isRaidRoster. | GET /api/attendance/members with no view returns the stored roster objects. | Both require a signed-in session (401 otherwise).
source_draft: delta-2026-10-03/mints.json
ssot_status: published
sot: Develop@9b8e7ae9ca2f9ccf046c5b609cdda545ced6eae9
<<<
RELATIONS:
- TYPE: Parent
  VALUE: USR-ROO-025

[[/SECTION]]

[[SECTION]]
TITLE: Scheduler/RSVP (REQ-ROO-114 .. REQ-ROO-122, REQ-ROO-176 .. REQ-ROO-178, REQ-ROO-183, REQ-ROO-189)

[REQUIREMENT]
UID: REQ-ROO-114
STATUS: Active
TITLE: REQ-ROO-114: `POST /api/attendance/ensure-week` materializes scheduler week instances for a w
STATEMENT: >>>
`POST /api/attendance/ensure-week` materializes scheduler week instances for a week.
<<<
COMMENT: >>>
domain: Scheduler/RSVP
priority: must
type: system
constraints: Live Develop behavior only; Do not import Firebase Requirements.md wording
acceptance_criteria: `POST /api/attendance/ensure-week` materializes scheduler week instances for a week.
source_draft: D-REQ-114
ssot_status: published
sot: Develop@a8a1edd713d6db6db61d42ed4eacf6a9e8737d07
<<<
RELATIONS:
- TYPE: Parent
  VALUE: USR-ROO-028

[REQUIREMENT]
UID: REQ-ROO-115
STATUS: Active
TITLE: REQ-ROO-115: `GET /api/attendance/week-instances` returns week instances (auto-ensure if need
STATEMENT: >>>
`GET /api/attendance/week-instances` returns week instances (auto-ensure if needed).
<<<
COMMENT: >>>
domain: Scheduler/RSVP
priority: must
type: system
constraints: Live Develop behavior only; Do not import Firebase Requirements.md wording
acceptance_criteria: `GET /api/attendance/week-instances` returns week instances (auto-ensure if needed).
source_draft: D-REQ-115
ssot_status: published
sot: Develop@a8a1edd713d6db6db61d42ed4eacf6a9e8737d07
<<<
RELATIONS:
- TYPE: Parent
  VALUE: USR-ROO-028

[REQUIREMENT]
UID: REQ-ROO-116
STATUS: Active
TITLE: REQ-ROO-116: GET /api/attendance/commitments returns commitments whose event date falls in th
STATEMENT: >>>
GET /api/attendance/commitments returns commitments whose event date falls in the week of weekMonday (query param, or the current week in the guild timezone), plus etag and weekMonday.
<<<
COMMENT: >>>
domain: Scheduler/RSVP
priority: must
type: system
constraints: Live Develop behavior only; Do not import Firebase Requirements.md wording
acceptance_criteria: GET /api/attendance/commitments returns commitments whose event date falls in the week of weekMonday (query param, or the current week in the guild timezone), plus etag and weekMonday. | If If-None-Match matches that week's commitment fingerprint, the response is 304 with an empty body. | The response is not the all-weeks RSVP tree.
source_draft: D-REQ-116
ssot_status: published
sot: Develop@3a3169d9b50670c8e6f6e4c45a0472b6c36b2630
<<<
RELATIONS:
- TYPE: Parent
  VALUE: USR-ROO-028

[REQUIREMENT]
UID: REQ-ROO-117
STATUS: Active
TITLE: REQ-ROO-117: `POST /api/attendance/commit-availability` logs Confirmed / Leave / related RSVP
STATEMENT: >>>
`POST /api/attendance/commit-availability` logs Confirmed / Leave / related RSVP decisions (via attendanceDecision rules + leave credits).
<<<
COMMENT: >>>
domain: Scheduler/RSVP
priority: must
type: system
constraints: Live Develop behavior only; Do not import Firebase Requirements.md wording
acceptance_criteria: `POST /api/attendance/commit-availability` logs Confirmed / Leave / related RSVP decisions (via attendanceDecision rules + leave credits).
source_draft: D-REQ-117
ssot_status: published
sot: Develop@a8a1edd713d6db6db61d42ed4eacf6a9e8737d07
<<<
RELATIONS:
- TYPE: Parent
  VALUE: USR-ROO-028

[REQUIREMENT]
UID: REQ-ROO-118
STATUS: Active
TITLE: REQ-ROO-118: Canonical RSVP statuses: Confirmed, Leave, NoConfirm, None (`@guildname/shared/a
STATEMENT: >>>
Canonical RSVP statuses: Confirmed, Leave, NoConfirm, None (`@guildname/shared/attendanceStatus`).
<<<
COMMENT: >>>
domain: Scheduler/RSVP
priority: must
type: system
constraints: Live Develop behavior only; Do not import Firebase Requirements.md wording
acceptance_criteria: Canonical RSVP statuses: Confirmed, Leave, NoConfirm, None (`@guildname/shared/attendanceStatus`).
source_draft: D-REQ-118
ssot_status: published
sot: Develop@a8a1edd713d6db6db61d42ed4eacf6a9e8737d07
<<<
RELATIONS:
- TYPE: Parent
  VALUE: USR-ROO-028

[REQUIREMENT]
UID: REQ-ROO-119
STATUS: Active
TITLE: REQ-ROO-119: The Discord 60-second tenant ticker does not auto-close expired RSVP deadlines.
STATEMENT: >>>
The Discord 60-second tenant ticker does not auto-close expired RSVP deadlines.
<<<
COMMENT: >>>
domain: Scheduler/RSVP
priority: must
type: system
constraints: Live Develop behavior only; Do not import Firebase Requirements.md wording
acceptance_criteria: The Discord 60-second tenant ticker does not auto-close expired RSVP deadlines. | closeExpiredDeadlines remains a callable function, but nothing in the minute loop invokes it.
source_draft: D-REQ-119
ssot_status: published
sot: Develop@56261347f46af5fb72d96b653fd48e8fda273d5c
<<<
RELATIONS:
- TYPE: Parent
  VALUE: USR-ROO-028

[REQUIREMENT]
UID: REQ-ROO-120
STATUS: Active
TITLE: REQ-ROO-120: Special events CRUD under `/api/attendance/special-events` (list/add/update/dele
STATEMENT: >>>
Special events CRUD under `/api/attendance/special-events` (list/add/update/delete) with officer writes.
<<<
COMMENT: >>>
domain: Scheduler/RSVP
priority: must
type: system
constraints: Live Develop behavior only; Do not import Firebase Requirements.md wording
acceptance_criteria: Special events CRUD under `/api/attendance/special-events` (list/add/update/delete) with officer writes.
source_draft: D-REQ-120
ssot_status: published
sot: Develop@a8a1edd713d6db6db61d42ed4eacf6a9e8737d07
<<<
RELATIONS:
- TYPE: Parent
  VALUE: USR-ROO-029

[REQUIREMENT]
UID: REQ-ROO-121
STATUS: Active
TITLE: REQ-ROO-121: Officer `POST /api/attendance/announce-week` triggers weekly attendance Discord 
STATEMENT: >>>
Officer `POST /api/attendance/announce-week` triggers weekly attendance Discord card/thread flow.
<<<
COMMENT: >>>
domain: Scheduler/RSVP
priority: must
type: system
constraints: Live Develop behavior only; Do not import Firebase Requirements.md wording
acceptance_criteria: Officer `POST /api/attendance/announce-week` triggers weekly attendance Discord card/thread flow.
source_draft: D-REQ-121
ssot_status: published
sot: Develop@a8a1edd713d6db6db61d42ed4eacf6a9e8737d07
<<<
RELATIONS:
- TYPE: Parent
  VALUE: USR-ROO-029

[REQUIREMENT]
UID: REQ-ROO-122
STATUS: Active
TITLE: REQ-ROO-122: Scheduler UI at `/attendance/scheduler`.
STATEMENT: >>>
Scheduler UI at `/attendance/scheduler`.
<<<
COMMENT: >>>
domain: Scheduler/RSVP
priority: must
type: software
constraints: Live Develop behavior only; Do not import Firebase Requirements.md wording
acceptance_criteria: Scheduler UI at `/attendance/scheduler`.
source_draft: D-REQ-122
ssot_status: published
sot: Develop@a8a1edd713d6db6db61d42ed4eacf6a9e8737d07
<<<
RELATIONS:
- TYPE: Parent
  VALUE: USR-ROO-029

[REQUIREMENT]
UID: REQ-ROO-176
STATUS: Active
TITLE: REQ-ROO-176: GVG Readiness stays on the cycle War after the RSVP deadline
STATEMENT: >>>
GVG Readiness stays on the cycle War after the RSVP deadline
<<<
COMMENT: >>>
domain: Scheduler/RSVP
priority: unspecified
type: system
constraints: A cycle targets the war only when needsSetup is not true, the cycle is not force-locked, and warDate, activeEventId, and warStartTime are all set.; The instance is loaded or materialized for the week of that war date, not blindly for the current week.; Board fingerprint includes event key, date, timeStart, title, locked-vs-open, and each member RSVP status.
acceptance_criteria: When the raid cycle targets a war, the GVG Readiness card shows that war even after its RSVP deadline, and the confirm/leave buttons are locked. | If that war's scheduler instance is missing or isCancelled, the card target is missing and does not fall through to the Set Active published composition or the next open RSVP. | When the cycle does not target a war, the card still prefers the anchored published composition, else the next event with an open RSVP window. | The readiness message is edited when the war date, start time, title, or locked/open flag changes, even if the RSVP map is unchanged.
source_draft: delta-2026-10-03/mints.json
ssot_status: published
sot: Develop@9b8e7ae9ca2f9ccf046c5b609cdda545ced6eae9
<<<
RELATIONS:
- TYPE: Parent
  VALUE: USR-ROO-028

[REQUIREMENT]
UID: REQ-ROO-177
STATUS: Active
TITLE: REQ-ROO-177: Rematerializing a week deletes stale non-special instances
STATEMENT: >>>
Rematerializing a week deletes stale non-special instances
<<<
COMMENT: >>>
domain: Scheduler/RSVP
priority: unspecified
type: system
constraints: Rows with isSpecial true or source 'special' are not deleted by this sweep.
acceptance_criteria: When a week is materialized, a non-special scheduler instance whose key is no longer in the generated week map is removed. | Special-event instances in that week are left in place.
source_draft: delta-2026-10-03/mints.json
ssot_status: published
sot: Develop@9b8e7ae9ca2f9ccf046c5b609cdda545ced6eae9
<<<
RELATIONS:
- TYPE: Parent
  VALUE: USR-ROO-028

[REQUIREMENT]
UID: REQ-ROO-178
STATUS: Active
TITLE: REQ-ROO-178: Scheduler and Raid Compose use raid phase 3 when the event is a raid
STATEMENT: >>>
Scheduler and Raid Compose use raid phase 3 when the event is a raid
<<<
COMMENT: >>>
domain: Scheduler/RSVP
priority: unspecified
type: software
constraints: isRaidEnabled(event) selects event.raid.phases[3]; otherwise event.phases[3] is used.; Scheduler business-hours fallback when phase 3 is missing remains 20:55–22:15. The day-focus time fallback remains 21:30–23:00.
acceptance_criteria: Scheduler weekly blocks, business-hour shading, and the RSVP deadline clock use raid.phases[3] day/time for a raid-enabled event, not a legacy phases[3] on the event root. | Raid Compose's generated war dates and default start time use that same raid phase 3.
source_draft: delta-2026-10-03/mints.json
ssot_status: published
sot: Develop@9b8e7ae9ca2f9ccf046c5b609cdda545ced6eae9
<<<
RELATIONS:
- TYPE: Parent
  VALUE: USR-ROO-029

[REQUIREMENT]
UID: REQ-ROO-183
STATUS: Active
TITLE: REQ-ROO-183: Scheduler does not re-GET commitments while the page stays open
STATEMENT: >>>
Scheduler does not re-GET commitments while the page stays open
<<<
COMMENT: >>>
domain: Scheduler/RSVP
priority: unspecified
type: software
constraints: The page asks settings for fields events, specialEventCategories, and timezone only.; The commitments request includes weekMonday when the page already has one.
acceptance_criteria: Leaving the Scheduler open does not repeat GET /api/attendance/commitments on a timer. | Commitments load when the page opens, and again when weekMonday changes. Changing week clears the stored ETag before that fetch so the new week is not answered with the previous week's 304.
source_draft: delta-2026-10-03/mints.json
ssot_status: published
sot: Develop@9b8e7ae9ca2f9ccf046c5b609cdda545ced6eae9
<<<
RELATIONS:
- TYPE: Parent
  VALUE: USR-ROO-029

[REQUIREMENT]
UID: REQ-ROO-189
STATUS: Active
TITLE: REQ-ROO-189: Attendance-card RSVP posts a GEN-room line at most once a minute
STATEMENT: >>>
Attendance-card RSVP posts a GEN-room line at most once a minute
<<<
COMMENT: >>>
domain: Scheduler/RSVP
priority: unspecified
type: system
constraints: Cooldown key is snowflake id plus the card composite key. Window is 60 seconds.; The line uses the raid cycle's activeEventTitle and warDate, not the button's event key. Missing title becomes 'the raid'. Missing name becomes 'A raider'.; Date format is Mon DD, YYYY (example shape Sep 23, 2026). Unparseable date becomes an em dash.; Confirmed is Available. Leave is Unavailable. If DISCORD_WARANNOUNCE_CHANNEL_ID is set, the line ends with ' Confirm yours at <#id>.' Otherwise that clause is omitted.; A no-op press that does not change status does not announce. A failed applyAttendanceDecision does not announce.
acceptance_criteria: After a member's GVG card press changes them to Confirmed, GEN room receives the Available sentence for the cycle war title and war date. | A press that changes them to Leave receives the Unavailable sentence. | A second successful change for the same member and card within 60 seconds does not send another GEN-room line.
source_draft: delta-2026-10-03/mints.json
ssot_status: published
sot: Develop@9b8e7ae9ca2f9ccf046c5b609cdda545ced6eae9
<<<
RELATIONS:
- TYPE: Parent
  VALUE: USR-ROO-028

[[/SECTION]]

[[SECTION]]
TITLE: Raid compose/Party (REQ-ROO-123 .. REQ-ROO-132, REQ-ROO-175, REQ-ROO-182, REQ-ROO-186, REQ-ROO-191 .. REQ-ROO-192)

[REQUIREMENT]
UID: REQ-ROO-123
STATUS: Active
TITLE: REQ-ROO-123: Compositions CRUD: list/create/save/duplicate/delete under `/api/attendance/comp
STATEMENT: >>>
Compositions CRUD: list/create/save/duplicate/delete under `/api/attendance/compositions*`.
<<<
COMMENT: >>>
domain: Raid compose/Party
priority: must
type: system
constraints: Live Develop behavior only; Do not import Firebase Requirements.md wording
acceptance_criteria: Compositions CRUD: list/create/save/duplicate/delete under `/api/attendance/compositions*`.
source_draft: D-REQ-123
ssot_status: published
sot: Develop@a8a1edd713d6db6db61d42ed4eacf6a9e8737d07
<<<
RELATIONS:
- TYPE: Parent
  VALUE: USR-ROO-030

[REQUIREMENT]
UID: REQ-ROO-124
STATUS: Active
TITLE: REQ-ROO-124: Composition tabs enforce cross-tab unique members (`findCrossTabDuplicates`).
STATEMENT: >>>
Composition tabs enforce cross-tab unique members (`findCrossTabDuplicates`).
<<<
COMMENT: >>>
domain: Raid compose/Party
priority: must
type: system
constraints: Live Develop behavior only; Do not import Firebase Requirements.md wording
acceptance_criteria: Composition tabs enforce cross-tab unique members (`findCrossTabDuplicates`).
source_draft: D-REQ-124
ssot_status: published
sot: Develop@a8a1edd713d6db6db61d42ed4eacf6a9e8737d07
<<<
RELATIONS:
- TYPE: Parent
  VALUE: USR-ROO-030

[REQUIREMENT]
UID: REQ-ROO-125
STATUS: Active
TITLE: REQ-ROO-125: Compose session APIs: get/create/save/close/send/deploy-roster under `/api/atten
STATEMENT: >>>
Compose session APIs: get/create/save/close/send/deploy-roster under `/api/attendance/compose*`.
<<<
COMMENT: >>>
domain: Raid compose/Party
priority: must
type: system
constraints: Live Develop behavior only; Do not import Firebase Requirements.md wording
acceptance_criteria: Compose session APIs: get/create/save/close/send/deploy-roster under `/api/attendance/compose*`.
source_draft: D-REQ-125
ssot_status: published
sot: Develop@a8a1edd713d6db6db61d42ed4eacf6a9e8737d07
<<<
RELATIONS:
- TYPE: Parent
  VALUE: USR-ROO-030

[REQUIREMENT]
UID: REQ-ROO-126
STATUS: Active
TITLE: REQ-ROO-126: GET /api/attendance/published returns the published record for the current raid-
STATEMENT: >>>
GET /api/attendance/published returns the published record for the current raid-cycle published id, plus any extra ids in the ids query, and the anchor.
<<<
COMMENT: >>>
domain: Raid compose/Party
priority: must
type: system
constraints: Live Develop behavior only; Do not import Firebase Requirements.md wording
acceptance_criteria: GET /api/attendance/published returns the published record for the current raid-cycle published id, plus any extra ids in the ids query, and the anchor. | Published ids outside that set are not included.
source_draft: D-REQ-126
ssot_status: published
sot: Develop@3a3169d9b50670c8e6f6e4c45a0472b6c36b2630
<<<
RELATIONS:
- TYPE: Parent
  VALUE: USR-ROO-031

[REQUIREMENT]
UID: REQ-ROO-127
STATUS: Active
TITLE: REQ-ROO-127: Published announce attendance / announce party endpoints post Discord cards for 
STATEMENT: >>>
Published announce attendance / announce party endpoints post Discord cards for a published id.
<<<
COMMENT: >>>
domain: Raid compose/Party
priority: must
type: system
constraints: Live Develop behavior only; Do not import Firebase Requirements.md wording
acceptance_criteria: Published announce attendance / announce party endpoints post Discord cards for a published id.
source_draft: D-REQ-127
ssot_status: published
sot: Develop@a8a1edd713d6db6db61d42ed4eacf6a9e8737d07
<<<
RELATIONS:
- TYPE: Parent
  VALUE: USR-ROO-031

[REQUIREMENT]
UID: REQ-ROO-128
STATUS: Active
TITLE: REQ-ROO-128: Published add/remove config and save-grids endpoints mutate published snapshot.
STATEMENT: >>>
Published add/remove config and save-grids endpoints mutate published snapshot.
<<<
COMMENT: >>>
domain: Raid compose/Party
priority: must
type: system
constraints: Live Develop behavior only; Do not import Firebase Requirements.md wording
acceptance_criteria: Published add/remove config and save-grids endpoints mutate published snapshot.
source_draft: D-REQ-128
ssot_status: published
sot: Develop@a8a1edd713d6db6db61d42ed4eacf6a9e8737d07
<<<
RELATIONS:
- TYPE: Parent
  VALUE: USR-ROO-031

[REQUIREMENT]
UID: REQ-ROO-129
STATUS: Active
TITLE: REQ-ROO-129: GET /api/war-room/init returns the raid cycle, the published record for cycle.pu
STATEMENT: >>>
GET /api/war-room/init returns the raid cycle, the published record for cycle.publishedId when it exists, the live session, members, jobs, the current week's commitments, the selected war rooms, automation status, and etag.
<<<
COMMENT: >>>
domain: Raid compose/Party
priority: must
type: system
constraints: Live Develop behavior only; Do not import Firebase Requirements.md wording
acceptance_criteria: GET /api/war-room/init returns the raid cycle, the published record for cycle.publishedId when it exists, the live session, members, jobs, the current week's commitments, the selected war rooms, automation status, and etag. | Commitments are not the all-weeks tree. | A matching If-None-Match returns 304 and no JSON body.
source_draft: D-REQ-129
ssot_status: published
sot: Develop@3a3169d9b50670c8e6f6e4c45a0472b6c36b2630
<<<
RELATIONS:
- TYPE: Parent
  VALUE: USR-ROO-031

[REQUIREMENT]
UID: REQ-ROO-130
STATUS: Active
TITLE: REQ-ROO-130: War Room automation may create live raid from published composition without HTTP
STATEMENT: >>>
War Room automation may create live raid from published composition without HTTP-to-self (`createLiveRaidFromPublished`).
<<<
COMMENT: >>>
domain: Raid compose/Party
priority: must
type: system
constraints: Live Develop behavior only; Do not import Firebase Requirements.md wording
acceptance_criteria: War Room automation may create live raid from published composition without HTTP-to-self (`createLiveRaidFromPublished`).
source_draft: D-REQ-130
ssot_status: published
sot: Develop@a8a1edd713d6db6db61d42ed4eacf6a9e8737d07
<<<
RELATIONS:
- TYPE: Parent
  VALUE: USR-ROO-031

[REQUIREMENT]
UID: REQ-ROO-131
STATUS: Active
TITLE: REQ-ROO-131: Frontend War Room at `/attendance/war-room`; legacy `/attendance/compose` and `/
STATEMENT: >>>
Frontend War Room at `/attendance/war-room`; legacy `/attendance/compose` and `/attendance/liveraid` redirect there.
<<<
COMMENT: >>>
domain: Raid compose/Party
priority: must
type: software
constraints: Live Develop behavior only; Do not import Firebase Requirements.md wording
acceptance_criteria: Frontend War Room at `/attendance/war-room`; legacy `/attendance/compose` and `/attendance/liveraid` redirect there.
source_draft: D-REQ-131
ssot_status: published
sot: Develop@a8a1edd713d6db6db61d42ed4eacf6a9e8737d07
<<<
RELATIONS:
- TYPE: Parent
  VALUE: USR-ROO-031

[REQUIREMENT]
UID: REQ-ROO-132
STATUS: Active
TITLE: REQ-ROO-132: Raid Config UI at `/attendance/raidparty`.
STATEMENT: >>>
Raid Config UI at `/attendance/raidparty`.
<<<
COMMENT: >>>
domain: Raid compose/Party
priority: must
type: software
constraints: Live Develop behavior only; Do not import Firebase Requirements.md wording
acceptance_criteria: Raid Config UI at `/attendance/raidparty`.
source_draft: D-REQ-132
ssot_status: published
sot: Develop@a8a1edd713d6db6db61d42ed4eacf6a9e8737d07
<<<
RELATIONS:
- TYPE: Parent
  VALUE: USR-ROO-031

[REQUIREMENT]
UID: REQ-ROO-175
STATUS: Active
TITLE: REQ-ROO-175: War Room cycle stays on the next War whose end is still ahead
STATEMENT: >>>
War Room cycle stays on the next War whose end is still ahead
<<<
COMMENT: >>>
domain: Raid compose/Party
priority: unspecified
type: system
constraints: Ended means now is strictly after phase-3 timeEnd on the war end date in the guild timezone.; The search walks at most three Monday-weeks forward.; While currentPhase is 3, that occurrence is kept even if its end has passed.; Phase-1 prep date is the chosen war date walked backward (weekday wrap of 7) to the phase-1 weekday, not a separately shifted week.
acceptance_criteria: After a war's phase-3 end, and when the cycle is not in phase 3, warDate, war start/end, and published id roll to the next occurrence that has not ended. | A Tuesday war that has already ended does not remain the current war just because Sunday sits at both the start of the minute circle and the end of the Monday week. | During phase 3 the cycle keeps the in-progress war date even after warEndsAt. | If no occurrence qualifies within three weeks, the cycle falls back to the war weekday in the current Monday-week.
source_draft: delta-2026-10-03/mints.json
ssot_status: published
sot: Develop@9b8e7ae9ca2f9ccf046c5b609cdda545ced6eae9
<<<
RELATIONS:
- TYPE: Parent
  VALUE: USR-ROO-031

[REQUIREMENT]
UID: REQ-ROO-182
STATUS: Active
TITLE: REQ-ROO-182: War Room does not re-GET init or voice presence while the page stays open
STATEMENT: >>>
War Room does not re-GET init or voice presence while the page stays open
<<<
COMMENT: >>>
domain: Raid compose/Party
priority: unspecified
type: software
constraints: GET /api/war-room/init may return 304 when If-None-Match equals the fingerprint of members, this week's commitments, config, the war-room docs, published id, phase, and war date.
acceptance_criteria: Leaving War Room open does not repeat GET /api/war-room/init and does not repeat the voice-presence poll. | Init still loads once when the page is opened for a signed-in user.
source_draft: delta-2026-10-03/mints.json
ssot_status: published
sot: Develop@9b8e7ae9ca2f9ccf046c5b609cdda545ced6eae9
<<<
RELATIONS:
- TYPE: Parent
  VALUE: USR-ROO-031

[REQUIREMENT]
UID: REQ-ROO-186
STATUS: Active
TITLE: REQ-ROO-186: Composition list can omit grids
STATEMENT: >>>
Composition list can omit grids
<<<
COMMENT: >>>
domain: Raid compose/Party
priority: unspecified
type: system
constraints: fields=list applies only when id is absent.; A list row is { id, title } with title defaulting to empty string.
acceptance_criteria: GET /api/attendance/compositions?fields=list returns every config as id and title only, with no grids or slot maps. | GET /api/attendance/compositions?id={id} returns that one full composition, or an empty compositions object when the id does not exist. | GET with neither id nor fields=list still returns full compositions.
source_draft: delta-2026-10-03/mints.json
ssot_status: published
sot: Develop@9b8e7ae9ca2f9ccf046c5b609cdda545ced6eae9
<<<
RELATIONS:
- TYPE: Parent
  VALUE: USR-ROO-030

[REQUIREMENT]
UID: REQ-ROO-191
STATUS: Active
TITLE: REQ-ROO-191: War Room publish keeps only the Raid Party config assigned in settings
STATEMENT: >>>
War Room publish keeps only the Raid Party config assigned in settings
<<<
COMMENT: >>>
domain: Raid compose/Party
priority: unspecified
type: system
constraints: Target config id is cycle.configId. Missing id fails the publish with 'No Raid Party config is assigned in Game Settings.'; Sync runs in phases 1 through 3 only when the phase is 1 or 2, or no Active live session exists. During phase 3 with an Active live session the published snapshot is left alone.; Already holding exactly that one config still sets the published anchor active.
acceptance_criteria: After a successful war-room publish sync, the published composition's grids contain only the settings Raid Party config; other configs that were on that published id are removed. | If that config is already the only one present, it is not re-added, and the anchor is set to that published id. | During phase 3 while a live session is Active, automation does not add or remove configs on the published composition.
source_draft: delta-2026-10-03/mints.json
ssot_status: published
sot: Develop@9b8e7ae9ca2f9ccf046c5b609cdda545ced6eae9
<<<
RELATIONS:
- TYPE: Parent
  VALUE: USR-ROO-031

[REQUIREMENT]
UID: REQ-ROO-192
STATUS: Active
TITLE: REQ-ROO-192: War Room republish and live-raid auto-start run once per cycle key
STATEMENT: >>>
War Room republish and live-raid auto-start run once per cycle key
<<<
COMMENT: >>>
domain: Raid compose/Party
priority: unspecified
type: system
constraints: Cycle key is currentPhase, activeEventId, publishedId, configId, and warDate joined by '|'.; The live-start key is recorded before createLiveRaidFromPublished returns. An empty warRoomIds list returns before the key is recorded, so a later non-empty list can still start.; ensureGvgReadinessBoardIfMissing runs only inside the successful publish branch, not on every minute tick.
acceptance_criteria: While the cycle key is unchanged, later 60-second ticks do not call publish/set-active again. | A failed live-raid auto-start is not attempted again on later ticks for that same cycle key. | A successful auto-start is not repeated for that same cycle key. | The GVG readiness board is not refreshed every minute; it is ensured only when that publish branch runs.
source_draft: delta-2026-10-03/mints.json
ssot_status: published
sot: Develop@9b8e7ae9ca2f9ccf046c5b609cdda545ced6eae9
<<<
RELATIONS:
- TYPE: Parent
  VALUE: USR-ROO-031

[[/SECTION]]

[[SECTION]]
TITLE: Live Raid/Voice (REQ-ROO-133 .. REQ-ROO-146, REQ-ROO-184, REQ-ROO-188, REQ-ROO-193, REQ-ROO-195)

[REQUIREMENT]
UID: REQ-ROO-133
STATUS: Active
TITLE: REQ-ROO-133: Officer `POST /api/live-raid/create` starts Active session from published compos
STATEMENT: >>>
Officer `POST /api/live-raid/create` starts Active session from published composition + ≥1 war room; rejects duplicates / missing grids / cross-tab dupes.
<<<
COMMENT: >>>
domain: Live Raid/Voice
priority: must
type: system
constraints: Live Develop behavior only; Do not import Firebase Requirements.md wording
acceptance_criteria: Officer `POST /api/live-raid/create` starts Active session from published composition + ≥1 war room; rejects duplicates / missing grids / cross-tab dupes.
source_draft: D-REQ-133
ssot_status: published
sot: Develop@a8a1edd713d6db6db61d42ed4eacf6a9e8737d07
<<<
RELATIONS:
- TYPE: Parent
  VALUE: USR-ROO-032

[REQUIREMENT]
UID: REQ-ROO-134
STATUS: Active
TITLE: REQ-ROO-134: `GET /api/live-raid/session` returns current live_session (war rooms normalized 
STATEMENT: >>>
`GET /api/live-raid/session` returns current live_session (war rooms normalized to Discord channel snowflakes).
<<<
COMMENT: >>>
domain: Live Raid/Voice
priority: must
type: system
constraints: Live Develop behavior only; Do not import Firebase Requirements.md wording
acceptance_criteria: `GET /api/live-raid/session` returns current live_session (war rooms normalized to Discord channel snowflakes).
source_draft: D-REQ-134
ssot_status: published
sot: Develop@a8a1edd713d6db6db61d42ed4eacf6a9e8737d07
<<<
RELATIONS:
- TYPE: Parent
  VALUE: USR-ROO-032

[REQUIREMENT]
UID: REQ-ROO-135
STATUS: Active
TITLE: REQ-ROO-135: Officer `POST /api/live-raid/update` patches session; rejects cross-tab duplicat
STATEMENT: >>>
Officer `POST /api/live-raid/update` patches session; rejects cross-tab duplicate grids.
<<<
COMMENT: >>>
domain: Live Raid/Voice
priority: must
type: system
constraints: Live Develop behavior only; Do not import Firebase Requirements.md wording
acceptance_criteria: Officer `POST /api/live-raid/update` patches session; rejects cross-tab duplicate grids.
source_draft: D-REQ-135
ssot_status: published
sot: Develop@a8a1edd713d6db6db61d42ed4eacf6a9e8737d07
<<<
RELATIONS:
- TYPE: Parent
  VALUE: USR-ROO-032

[REQUIREMENT]
UID: REQ-ROO-136
STATUS: Active
TITLE: REQ-ROO-136: Officer `POST /api/live-raid/cell-update` moves/clears a member slot across grid
STATEMENT: >>>
Officer `POST /api/live-raid/cell-update` moves/clears a member slot across grids atomically.
<<<
COMMENT: >>>
domain: Live Raid/Voice
priority: must
type: system
constraints: Live Develop behavior only; Do not import Firebase Requirements.md wording
acceptance_criteria: Officer `POST /api/live-raid/cell-update` moves/clears a member slot across grids atomically.
source_draft: D-REQ-136
ssot_status: published
sot: Develop@a8a1edd713d6db6db61d42ed4eacf6a9e8737d07
<<<
RELATIONS:
- TYPE: Parent
  VALUE: USR-ROO-032

[REQUIREMENT]
UID: REQ-ROO-137
STATUS: Active
TITLE: REQ-ROO-137: `GET /api/live-raid/voice-presence` returns present UIDs for resolved war-room c
STATEMENT: >>>
`GET /api/live-raid/voice-presence` returns present UIDs for resolved war-room channels (503 if circuit open).
<<<
COMMENT: >>>
domain: Live Raid/Voice
priority: must
type: system
constraints: Live Develop behavior only; Do not import Firebase Requirements.md wording
acceptance_criteria: `GET /api/live-raid/voice-presence` returns present UIDs for resolved war-room channels (503 if circuit open).
source_draft: D-REQ-137
ssot_status: published
sot: Develop@a8a1edd713d6db6db61d42ed4eacf6a9e8737d07
<<<
RELATIONS:
- TYPE: Parent
  VALUE: USR-ROO-033

[REQUIREMENT]
UID: REQ-ROO-138
STATUS: Active
TITLE: REQ-ROO-138: Monitoring schedule requires startsAt, endsAt, pollIntervalMinutes ≥ 15; arms ti
STATEMENT: >>>
Monitoring schedule requires startsAt, endsAt, pollIntervalMinutes ≥ 15; arms ticker scheduled/running/ended.
<<<
COMMENT: >>>
domain: Live Raid/Voice
priority: must
type: system
constraints: Live Develop behavior only; Do not import Firebase Requirements.md wording
acceptance_criteria: Monitoring schedule requires startsAt, endsAt, pollIntervalMinutes ≥ 15; arms ticker scheduled/running/ended.
source_draft: D-REQ-138
ssot_status: published
sot: Develop@a8a1edd713d6db6db61d42ed4eacf6a9e8737d07
<<<
RELATIONS:
- TYPE: Parent
  VALUE: USR-ROO-033

[REQUIREMENT]
UID: REQ-ROO-139
STATUS: Active
TITLE: REQ-ROO-139: Voice pulses increment `totalPulses` and per-uid tallies; dedupe within half-int
STATEMENT: >>>
Voice pulses increment `totalPulses` and per-uid tallies; dedupe within half-interval; skip when Discord circuit open.
<<<
COMMENT: >>>
domain: Live Raid/Voice
priority: must
type: system
constraints: Live Develop behavior only; Do not import Firebase Requirements.md wording
acceptance_criteria: Voice pulses increment `totalPulses` and per-uid tallies; dedupe within half-interval; skip when Discord circuit open.
source_draft: D-REQ-139
ssot_status: published
sot: Develop@a8a1edd713d6db6db61d42ed4eacf6a9e8737d07
<<<
RELATIONS:
- TYPE: Parent
  VALUE: USR-ROO-033

[REQUIREMENT]
UID: REQ-ROO-140
STATUS: Active
TITLE: REQ-ROO-140: Officer `POST /api/live-raid/end` archives session to `attendance/session_archiv
STATEMENT: >>>
Officer `POST /api/live-raid/end` archives session to `attendance/session_archive` with tallies, commitments snapshot, expectedPulses, endedEarly flag; clears live_session.
<<<
COMMENT: >>>
domain: Live Raid/Voice
priority: must
type: system
constraints: Live Develop behavior only; Do not import Firebase Requirements.md wording
acceptance_criteria: Officer `POST /api/live-raid/end` archives session to `attendance/session_archive` with tallies, commitments snapshot, expectedPulses, endedEarly flag; clears live_session.
source_draft: D-REQ-140
ssot_status: published
sot: Develop@a8a1edd713d6db6db61d42ed4eacf6a9e8737d07
<<<
RELATIONS:
- TYPE: Parent
  VALUE: USR-ROO-034

[REQUIREMENT]
UID: REQ-ROO-141
STATUS: Active
TITLE: REQ-ROO-141: Early end captures a final pulse when monitoring had started and end is before s
STATEMENT: >>>
Early end captures a final pulse when monitoring had started and end is before scheduled end.
<<<
COMMENT: >>>
domain: Live Raid/Voice
priority: must
type: system
constraints: Live Develop behavior only; Do not import Firebase Requirements.md wording
acceptance_criteria: Early end captures a final pulse when monitoring had started and end is before scheduled end.
source_draft: D-REQ-141
ssot_status: published
sot: Develop@a8a1edd713d6db6db61d42ed4eacf6a9e8737d07
<<<
RELATIONS:
- TYPE: Parent
  VALUE: USR-ROO-034

[REQUIREMENT]
UID: REQ-ROO-142
STATUS: Active
TITLE: REQ-ROO-142: Officer `POST /api/live-raid/cancel` clears live_session without archive.
STATEMENT: >>>
Officer `POST /api/live-raid/cancel` clears live_session without archive.
<<<
COMMENT: >>>
domain: Live Raid/Voice
priority: must
type: system
constraints: Live Develop behavior only; Do not import Firebase Requirements.md wording
acceptance_criteria: Officer `POST /api/live-raid/cancel` clears live_session without archive.
source_draft: D-REQ-142
ssot_status: published
sot: Develop@a8a1edd713d6db6db61d42ed4eacf6a9e8737d07
<<<
RELATIONS:
- TYPE: Parent
  VALUE: USR-ROO-034

[REQUIREMENT]
UID: REQ-ROO-143
STATUS: Active
TITLE: REQ-ROO-143: Boot resumes monitoring ticker if Active session still within window; auto-ends 
STATEMENT: >>>
Boot resumes monitoring ticker if Active session still within window; auto-ends if window already passed.
<<<
COMMENT: >>>
domain: Live Raid/Voice
priority: must
type: system
constraints: Live Develop behavior only; Do not import Firebase Requirements.md wording
acceptance_criteria: Boot resumes monitoring ticker if Active session still within window; auto-ends if window already passed.
source_draft: D-REQ-143
ssot_status: published
sot: Develop@a8a1edd713d6db6db61d42ed4eacf6a9e8737d07
<<<
RELATIONS:
- TYPE: Parent
  VALUE: USR-ROO-034

[REQUIREMENT]
UID: REQ-ROO-144
STATUS: Active
TITLE: REQ-ROO-144: A live raid is archived automatically when its monitoring end time is reached
STATEMENT: >>>
A live raid is archived automatically when its monitoring end time is reached
<<<
COMMENT: >>>
domain: Live Raid/Voice
priority: must
type: system
constraints: Live Develop behavior only; Do not import Firebase Requirements.md wording
acceptance_criteria: When a live raid's monitoring end time is reached, the session is archived automatically with no officer action.
source_draft: D-REQ-144
ssot_status: published
sot: Develop@a8a1edd713d6db6db61d42ed4eacf6a9e8737d07
<<<
RELATIONS:
- TYPE: Parent
  VALUE: USR-ROO-034

[REQUIREMENT]
UID: REQ-ROO-145
STATUS: Active
TITLE: REQ-ROO-145: GET /api/live-raid/history/all with no sessionId and without fields=full returns
STATEMENT: >>>
GET /api/live-raid/history/all with no sessionId and without fields=full returns at most limit sessions (default 12, clamped to 1–50), newest endedAt first.
<<<
COMMENT: >>>
domain: Live Raid/Voice
priority: must
type: system
constraints: Live Develop behavior only; Do not import Firebase Requirements.md wording
acceptance_criteria: GET /api/live-raid/history/all with no sessionId and without fields=full returns at most limit sessions (default 12, clamped to 1–50), newest endedAt first. | Each default session object has only id, eventTitle, eventDate, eventKey, endedAt, endedEarly, committedBy, totalPulses, expectedPulses, userTallies, commitments, and inGameStatus. Grids are not included. | fields=full, or a sessionId query, returns the stored archive row (one id when sessionId is set).
source_draft: D-REQ-145
ssot_status: published
sot: Develop@3a3169d9b50670c8e6f6e4c45a0472b6c36b2630
<<<
RELATIONS:
- TYPE: Parent
  VALUE: USR-ROO-034

[REQUIREMENT]
UID: REQ-ROO-146
STATUS: Active
TITLE: REQ-ROO-146: Frontend GVG History at `/attendance/history`; GVG Attendance OCR UI at `/attend
STATEMENT: >>>
Frontend GVG History at `/attendance/history`; GVG Attendance OCR UI at `/attendance/ocr-review`.
<<<
COMMENT: >>>
domain: Live Raid/Voice
priority: must
type: software
constraints: Live Develop behavior only; Do not import Firebase Requirements.md wording
acceptance_criteria: Frontend GVG History at `/attendance/history`; GVG Attendance OCR UI at `/attendance/ocr-review`.
source_draft: D-REQ-146
ssot_status: published
sot: Develop@a8a1edd713d6db6db61d42ed4eacf6a9e8737d07
<<<
RELATIONS:
- TYPE: Parent
  VALUE: USR-ROO-034

[REQUIREMENT]
UID: REQ-ROO-184
STATUS: Active
TITLE: REQ-ROO-184: Live Raid does not re-GET session, voice, or published data while the page stays
STATEMENT: >>>
Live Raid does not re-GET session, voice, or published data while the page stays open
<<<
COMMENT: >>>
domain: Live Raid/Voice
priority: unspecified
type: software
constraints: A 1-second local clock that only updates the on-screen now is allowed and is not a server poll.; History on this page requests /api/live-raid/history/all?limit=12.; Roster for the card view uses GET /api/attendance/members?view=card (REQ-ROO-187).
acceptance_criteria: With or without an active live session, leaving Live Raid open does not repeat GET of the live session, voice presence, published compositions, or commitments. | Those loads still happen when the page opens or the session identity changes.
source_draft: delta-2026-10-03/mints.json
ssot_status: published
sot: Develop@9b8e7ae9ca2f9ccf046c5b609cdda545ced6eae9
<<<
RELATIONS:
- TYPE: Parent
  VALUE: USR-ROO-032

[REQUIREMENT]
UID: REQ-ROO-188
STATUS: Active
TITLE: REQ-ROO-188: Attendance begin-raid does not start a presence ticker
STATEMENT: >>>
Attendance begin-raid does not start a presence ticker
<<<
COMMENT: >>>
domain: Live Raid/Voice
priority: unspecified
type: system
constraints: Any previous attendanceIntervalTicker is cleared and not replaced.
acceptance_criteria: POST /api/attendance/begin-raid stores the active attendance session and responds with message 'Live Raid active.' | That call does not start a 15-minute interval that increments attendance/active_session user tallies from voice channels.
source_draft: delta-2026-10-03/mints.json
ssot_status: published
sot: Develop@9b8e7ae9ca2f9ccf046c5b609cdda545ced6eae9
<<<
RELATIONS:
- TYPE: Parent
  VALUE: USR-ROO-033

[REQUIREMENT]
UID: REQ-ROO-193
STATUS: Active
TITLE: REQ-ROO-193: The minute loop does not re-read an idle live session
STATEMENT: >>>
The minute loop does not re-read an idle live session
<<<
COMMENT: >>>
domain: Live Raid/Voice
priority: unspecified
type: system
constraints: Watch starts unknown. The first automatic end-time check that does not find status Active sets the watch to absent. Active sets it to active.; createLiveRaidFromPublished of a new session, and a war-room read that finds Active, set the watch active. End and cancel set it absent.; This watch is in-process memory. Another process is not visible to it.
acceptance_criteria: After this process has observed that no Active live session exists, later 60-second ticks do not query attendance/live_session until this process starts one or otherwise marks the watch active. | While the watch is active and monitoringEndsAt is in the past, the session is still archived automatically (REQ-ROO-144) and then the watch is marked absent. | A non-Active document is treated as absent and is not polled again.
source_draft: delta-2026-10-03/mints.json
ssot_status: published
sot: Develop@9b8e7ae9ca2f9ccf046c5b609cdda545ced6eae9
<<<
RELATIONS:
- TYPE: Parent
  VALUE: USR-ROO-034

[REQUIREMENT]
UID: REQ-ROO-195
STATUS: Active
TITLE: REQ-ROO-195: Voice-monitoring ticks keep the tenant that armed them
STATEMENT: >>>
Voice-monitoring ticks keep the tenant that armed them
<<<
COMMENT: >>>
domain: Live Raid/Voice
priority: unspecified
type: system
constraints: tenantId is captured when the monitoring schedule is armed, including the delayed start interval (15s checks until startsAt).; If no tenant id was current at arm time, the tick runs without runWithTenant.
acceptance_criteria: After the HTTP or bot call that armed monitoring has finished, interval pulses and the delayed start still read and write the live session under the tenant that armed the schedule. | A pulse that asks to stop still clears the interval ticker.
source_draft: delta-2026-10-03/mints.json
ssot_status: published
sot: Develop@9b8e7ae9ca2f9ccf046c5b609cdda545ced6eae9
<<<
RELATIONS:
- TYPE: Parent
  VALUE: USR-ROO-033

[[/SECTION]]

[[SECTION]]
TITLE: OCR/GVG Attendance (REQ-ROO-147 .. REQ-ROO-151)

[REQUIREMENT]
UID: REQ-ROO-147
STATUS: Active
TITLE: REQ-ROO-147: Officer `GET /api/ocr-reviews/events` lists eligible OCR calendar events.
STATEMENT: >>>
Officer `GET /api/ocr-reviews/events` lists eligible OCR calendar events.
<<<
COMMENT: >>>
domain: OCR/GVG Attendance
priority: must
type: system
constraints: Live Develop behavior only; Do not import Firebase Requirements.md wording
acceptance_criteria: Officer `GET /api/ocr-reviews/events` lists eligible OCR calendar events.
source_draft: D-REQ-147
ssot_status: published
sot: Develop@a8a1edd713d6db6db61d42ed4eacf6a9e8737d07
<<<
RELATIONS:
- TYPE: Parent
  VALUE: USR-ROO-035

[REQUIREMENT]
UID: REQ-ROO-148
STATUS: Active
TITLE: REQ-ROO-148: Officer `POST /api/ocr-reviews/scan` accepts ≤8 images ≤8MB each, creates draft 
STATEMENT: >>>
Officer `POST /api/ocr-reviews/scan` accepts ≤8 images ≤8MB each, creates draft review tied to event.
<<<
COMMENT: >>>
domain: OCR/GVG Attendance
priority: must
type: system
constraints: Live Develop behavior only; Do not import Firebase Requirements.md wording
acceptance_criteria: Officer `POST /api/ocr-reviews/scan` accepts ≤8 images ≤8MB each, creates draft review tied to event.
source_draft: D-REQ-148
ssot_status: published
sot: Develop@a8a1edd713d6db6db61d42ed4eacf6a9e8737d07
<<<
RELATIONS:
- TYPE: Parent
  VALUE: USR-ROO-035

[REQUIREMENT]
UID: REQ-ROO-149
STATUS: Active
TITLE: REQ-ROO-149: Officer list/get draft reviews; patch present UIDs / assign unmatched; commit fi
STATEMENT: >>>
Officer list/get draft reviews; patch present UIDs / assign unmatched; commit finalizes; cancel/delete removes draft.
<<<
COMMENT: >>>
domain: OCR/GVG Attendance
priority: must
type: system
constraints: Live Develop behavior only; Do not import Firebase Requirements.md wording
acceptance_criteria: Officer list/get draft reviews; patch present UIDs / assign unmatched; commit finalizes; cancel/delete removes draft.
source_draft: D-REQ-149
ssot_status: published
sot: Develop@a8a1edd713d6db6db61d42ed4eacf6a9e8737d07
<<<
RELATIONS:
- TYPE: Parent
  VALUE: USR-ROO-035

[REQUIREMENT]
UID: REQ-ROO-150
STATUS: Active
TITLE: REQ-ROO-150: Commit writes in-game/attendance outcomes and refreshes Discord review message w
STATEMENT: >>>
Commit writes in-game/attendance outcomes and refreshes Discord review message when present.
<<<
COMMENT: >>>
domain: OCR/GVG Attendance
priority: must
type: system
constraints: Live Develop behavior only; Do not import Firebase Requirements.md wording
acceptance_criteria: Commit writes in-game/attendance outcomes and refreshes Discord review message when present.
source_draft: D-REQ-150
ssot_status: published
sot: Develop@a8a1edd713d6db6db61d42ed4eacf6a9e8737d07
<<<
RELATIONS:
- TYPE: Parent
  VALUE: USR-ROO-035

[REQUIREMENT]
UID: REQ-ROO-151
STATUS: Active
TITLE: REQ-ROO-151: Non-draft reviews are not editable (409).
STATEMENT: >>>
Non-draft reviews are not editable (409).
<<<
COMMENT: >>>
domain: OCR/GVG Attendance
priority: must
type: system
constraints: Live Develop behavior only; Do not import Firebase Requirements.md wording
acceptance_criteria: Non-draft reviews are not editable (409).
source_draft: D-REQ-151
ssot_status: published
sot: Develop@a8a1edd713d6db6db61d42ed4eacf6a9e8737d07
<<<
RELATIONS:
- TYPE: Parent
  VALUE: USR-ROO-035

[[/SECTION]]

[[SECTION]]
TITLE: Adventurer Guild (REQ-ROO-152 .. REQ-ROO-157, REQ-ROO-196)

[REQUIREMENT]
UID: REQ-ROO-152
STATUS: Active
TITLE: REQ-ROO-152: `GET /api/adventurer-guild/highlights` lists highlights newest-first for members
STATEMENT: >>>
`GET /api/adventurer-guild/highlights` lists highlights newest-first for members.
<<<
COMMENT: >>>
domain: Adventurer Guild
priority: must
type: system
constraints: Live Develop behavior only; Do not import Firebase Requirements.md wording
acceptance_criteria: `GET /api/adventurer-guild/highlights` lists highlights newest-first for members.
source_draft: D-REQ-152
ssot_status: published
sot: Develop@a8a1edd713d6db6db61d42ed4eacf6a9e8737d07
<<<
RELATIONS:
- TYPE: Parent
  VALUE: USR-ROO-036

[REQUIREMENT]
UID: REQ-ROO-153
STATUS: Active
TITLE: REQ-ROO-153: Authenticated `POST /api/adventurer-guild/highlights` uploads image/video ≤25MB 
STATEMENT: >>>
Authenticated `POST /api/adventurer-guild/highlights` uploads image/video ≤25MB to Supabase Storage and stores caption ≤280 chars.
<<<
COMMENT: >>>
domain: Adventurer Guild
priority: must
type: system
constraints: Live Develop behavior only; Do not import Firebase Requirements.md wording
acceptance_criteria: Authenticated `POST /api/adventurer-guild/highlights` uploads image/video ≤25MB to Supabase Storage and stores caption ≤280 chars.
source_draft: D-REQ-153
ssot_status: published
sot: Develop@a8a1edd713d6db6db61d42ed4eacf6a9e8737d07
<<<
RELATIONS:
- TYPE: Parent
  VALUE: USR-ROO-036

[REQUIREMENT]
UID: REQ-ROO-154
STATUS: Active
TITLE: REQ-ROO-154: Highlight delete allowed for creator or officer; deletes storage object + row.
STATEMENT: >>>
Highlight delete allowed for creator or officer; deletes storage object + row.
<<<
COMMENT: >>>
domain: Adventurer Guild
priority: must
type: system
constraints: Live Develop behavior only; Do not import Firebase Requirements.md wording
acceptance_criteria: Highlight delete allowed for creator or officer; deletes storage object + row.
source_draft: D-REQ-154
ssot_status: published
sot: Develop@a8a1edd713d6db6db61d42ed4eacf6a9e8737d07
<<<
RELATIONS:
- TYPE: Parent
  VALUE: USR-ROO-036

[REQUIREMENT]
UID: REQ-ROO-155
STATUS: Active
TITLE: REQ-ROO-155: `GET /api/adventurer-guild/events` returns native AG events + contributed schedu
STATEMENT: >>>
`GET /api/adventurer-guild/events` returns native AG events + contributed schedules from other enabled games in date range.
<<<
COMMENT: >>>
domain: Adventurer Guild
priority: must
type: system
constraints: Live Develop behavior only; Do not import Firebase Requirements.md wording
acceptance_criteria: `GET /api/adventurer-guild/events` returns native AG events + contributed schedules from other enabled games in date range.
source_draft: D-REQ-155
ssot_status: published
sot: Develop@a8a1edd713d6db6db61d42ed4eacf6a9e8737d07
<<<
RELATIONS:
- TYPE: Parent
  VALUE: USR-ROO-037

[REQUIREMENT]
UID: REQ-ROO-156
STATUS: Active
TITLE: REQ-ROO-156: Officer CRUD for native AG events (title≤120, description≤500, date/time/allDay)
STATEMENT: >>>
Officer CRUD for native AG events (title≤120, description≤500, date/time/allDay).
<<<
COMMENT: >>>
domain: Adventurer Guild
priority: must
type: system
constraints: Live Develop behavior only; Do not import Firebase Requirements.md wording
acceptance_criteria: Officer CRUD for native AG events (title≤120, description≤500, date/time/allDay).
source_draft: D-REQ-156
ssot_status: published
sot: Develop@a8a1edd713d6db6db61d42ed4eacf6a9e8737d07
<<<
RELATIONS:
- TYPE: Parent
  VALUE: USR-ROO-037

[REQUIREMENT]
UID: REQ-ROO-157
STATUS: Active
TITLE: REQ-ROO-157: SPA routes `/games/adventurer-guild` (Highlights) and `/games/adventurer-guild/e
STATEMENT: >>>
SPA routes `/games/adventurer-guild` (Highlights) and `/games/adventurer-guild/events`; highlights alias redirects to home.
<<<
COMMENT: >>>
domain: Adventurer Guild
priority: must
type: software
constraints: Live Develop behavior only; Do not import Firebase Requirements.md wording
acceptance_criteria: SPA routes `/games/adventurer-guild` (Highlights) and `/games/adventurer-guild/events`; highlights alias redirects to home.
source_draft: D-REQ-157
ssot_status: published
sot: Develop@a8a1edd713d6db6db61d42ed4eacf6a9e8737d07
<<<
RELATIONS:
- TYPE: Parent
  VALUE: USR-ROO-037

[REQUIREMENT]
UID: REQ-ROO-196
STATUS: Active
TITLE: REQ-ROO-196: Highlight videos preload metadata only
STATEMENT: >>>
Highlight videos preload metadata only
<<<
COMMENT: >>>
domain: Adventurer Guild
priority: unspecified
type: software
constraints: Upload cacheControl value is 31536000.; Size cap remains 25MB (REQ-ROO-153).
acceptance_criteria: A highlight video element on the gallery sets preload to metadata. | A highlight upload sends cacheControl 31536000 with the storage object.
source_draft: delta-2026-10-03/mints.json
ssot_status: published
sot: Develop@9b8e7ae9ca2f9ccf046c5b609cdda545ced6eae9
<<<
RELATIONS:
- TYPE: Parent
  VALUE: USR-ROO-036

[[/SECTION]]

[[SECTION]]
TITLE: Data isolation/Storage (REQ-VAL-158 .. REQ-VAL-166)

[REQUIREMENT]
UID: REQ-VAL-158
STATUS: Active
TITLE: REQ-VAL-158: Rows are stamped with tenant and game; handlers need an explicit game
STATEMENT: >>>
Rows are stamped with tenant and game; handlers need an explicit game
<<<
COMMENT: >>>
domain: Data isolation/Storage
priority: must
type: system
constraints: Live Develop behavior only; Do not import Firebase Requirements.md wording
acceptance_criteria: Every operational row is stamped with tenant and game. | Handlers run inside the tenant and an explicitly set game. | A handler that would read or write game data with no game set is refused with a 'select a game' error and writes nothing.
source_draft: D-REQ-158
ssot_status: published
sot: xWhiteSpace/ROOGuildApp@f38e1378c7cca457fbf8de8e8355d59994f77fc8
<<<
RELATIONS:
- TYPE: Parent
  VALUE: USR-VAL-038

[REQUIREMENT]
UID: REQ-VAL-159
STATUS: Active
TITLE: REQ-VAL-159: `x-tenant-id` header cannot silently switch away from session/current tenant whe
STATEMENT: >>>
`x-tenant-id` header cannot silently switch away from session/current tenant when mismatched.
<<<
COMMENT: >>>
domain: Data isolation/Storage
priority: must
type: system
constraints: Live Develop behavior only; Do not import Firebase Requirements.md wording
acceptance_criteria: `x-tenant-id` header cannot silently switch away from session/current tenant when mismatched.
source_draft: D-REQ-159
ssot_status: published
sot: Develop@a8a1edd713d6db6db61d42ed4eacf6a9e8737d07
<<<
RELATIONS:
- TYPE: Parent
  VALUE: USR-VAL-038

[REQUIREMENT]
UID: REQ-VAL-160
STATUS: Active
TITLE: REQ-VAL-160: Adds the per-game settings table; operational tables are keyed by game too.
STATEMENT: >>>
Adds the per-game settings table; operational tables are keyed by game too.
<<<
COMMENT: >>>
domain: Data isolation/Storage
priority: must
type: system
constraints: Live Develop behavior only; Do not import Firebase Requirements.md wording
acceptance_criteria: The schema has a per-game settings table keyed by tenant and game. | members, auction_requests, past_auction_awards, loot_history, attendance_commitments, schedule_instances, special_events and json_docs carry a game id in their key, default ragnarok-origin. | platform_state has no game id.
source_draft: D-REQ-160
ssot_status: published
sot: xWhiteSpace/ROOGuildApp@f38e1378c7cca457fbf8de8e8355d59994f77fc8
<<<
RELATIONS:
- TYPE: Parent
  VALUE: USR-VAL-039

[REQUIREMENT]
UID: REQ-VAL-161
STATUS: Active
TITLE: REQ-VAL-161: Flexible trees persist per tenant, game and path; the same path in two games is 
STATEMENT: >>>
Flexible trees persist per tenant, game and path; the same path in two games is two separate documents.
<<<
COMMENT: >>>
domain: Data isolation/Storage
priority: must
type: system
constraints: Live Develop behavior only; Do not import Firebase Requirements.md wording
acceptance_criteria: Flexible trees persist per tenant, game and path; the same path in two games is two separate documents.
source_draft: D-REQ-161
ssot_status: published
sot: xWhiteSpace/ROOGuildApp@f38e1378c7cca457fbf8de8e8355d59994f77fc8
<<<
RELATIONS:
- TYPE: Parent
  VALUE: USR-VAL-039

[REQUIREMENT]
UID: REQ-VAL-162
STATUS: Active
TITLE: REQ-VAL-162: Platform-wide Discord circuit / flags use `platform_state` (not per-tenant).
STATEMENT: >>>
Platform-wide Discord circuit / flags use `platform_state` (not per-tenant).
<<<
COMMENT: >>>
domain: Data isolation/Storage
priority: must
type: system
constraints: Live Develop behavior only; Do not import Firebase Requirements.md wording
acceptance_criteria: Platform-wide Discord circuit / flags use `platform_state` (not per-tenant).
source_draft: D-REQ-162
ssot_status: published
sot: Develop@a8a1edd713d6db6db61d42ed4eacf6a9e8737d07
<<<
RELATIONS:
- TYPE: Parent
  VALUE: USR-VAL-039

[REQUIREMENT]
UID: REQ-VAL-163
STATUS: Active
TITLE: REQ-VAL-163: Shared package exports attendance statuses, composition tab helpers, raid cycle 
STATEMENT: >>>
Shared package exports attendance statuses, composition tab helpers, raid cycle helpers, in-game alias helpers for FE/BE parity.
<<<
COMMENT: >>>
domain: Data isolation/Storage
priority: must
type: system
constraints: Live Develop behavior only; Do not import Firebase Requirements.md wording
acceptance_criteria: Shared package exports attendance statuses, composition tab helpers, raid cycle helpers, in-game alias helpers for FE/BE parity.
source_draft: D-REQ-163
ssot_status: published
sot: Develop@a8a1edd713d6db6db61d42ed4eacf6a9e8737d07
<<<
RELATIONS:
- TYPE: Parent
  VALUE: USR-VAL-040

[REQUIREMENT]
UID: REQ-VAL-164
STATUS: Active
TITLE: REQ-VAL-164: Backend `npm run test:isolation` exists for tenant A/B isolation check (README).
STATEMENT: >>>
Backend `npm run test:isolation` exists for tenant A/B isolation check (README).
<<<
COMMENT: >>>
domain: Data isolation/Storage
priority: must
type: system
constraints: Live Develop behavior only; Do not import Firebase Requirements.md wording
acceptance_criteria: Backend `npm run test:isolation` exists for tenant A/B isolation check (README).
source_draft: D-REQ-164
ssot_status: published
sot: Develop@a8a1edd713d6db6db61d42ed4eacf6a9e8737d07
<<<
RELATIONS:
- TYPE: Parent
  VALUE: USR-VAL-040

[REQUIREMENT]
UID: REQ-VAL-165
STATUS: Active
TITLE: REQ-VAL-165: Default workspace timezone seed is `Asia/Manila`; guild wall-clock helpers use t
STATEMENT: >>>
Default workspace timezone seed is `Asia/Manila`; guild wall-clock helpers use tenant timezone.
<<<
COMMENT: >>>
domain: Data isolation/Storage
priority: must
type: system
constraints: Live Develop behavior only; Do not import Firebase Requirements.md wording
acceptance_criteria: Default workspace timezone seed is `Asia/Manila`; guild wall-clock helpers use tenant timezone.
source_draft: D-REQ-165
ssot_status: published
sot: Develop@a8a1edd713d6db6db61d42ed4eacf6a9e8737d07
<<<
RELATIONS:
- TYPE: Parent
  VALUE: USR-VAL-040

[REQUIREMENT]
UID: REQ-VAL-166
STATUS: Active
TITLE: REQ-VAL-166: Default RO config seeds: items/events empty, defaultLeaveCredits=3, liveRaidMaxC
STATEMENT: >>>
Default RO config seeds: items/events empty, defaultLeaveCredits=3, liveRaidMaxConfigs=5, liveRaidMaxWarRooms=2, specialEventCategories, warRooms/jobs/roles placeholders, help embed URLs empty.
<<<
COMMENT: >>>
domain: Data isolation/Storage
priority: must
type: system
constraints: Live Develop behavior only; Do not import Firebase Requirements.md wording
acceptance_criteria: Default RO config seeds: items/events empty, defaultLeaveCredits=3, liveRaidMaxConfigs=5, liveRaidMaxWarRooms=2, specialEventCategories, warRooms/jobs/roles placeholders, help embed URLs empty.
source_draft: D-REQ-166
ssot_status: published
sot: Develop@a8a1edd713d6db6db61d42ed4eacf6a9e8737d07
<<<
RELATIONS:
- TYPE: Parent
  VALUE: USR-VAL-040

[[/SECTION]]

[[SECTION]]
TITLE: Frontend shell/UX (REQ-VAL-167 .. REQ-VAL-172)

[REQUIREMENT]
UID: REQ-VAL-167
STATUS: Active
TITLE: REQ-VAL-167: Landing is public full-bleed; authenticated users on `/landing` redirect to post
STATEMENT: >>>
Landing is public full-bleed; authenticated users on `/landing` redirect to post-login path.
<<<
COMMENT: >>>
domain: Frontend shell/UX
priority: must
type: system
constraints: Live Develop behavior only; Do not import Firebase Requirements.md wording
acceptance_criteria: Landing is public full-bleed; authenticated users on `/landing` redirect to post-login path.
source_draft: D-REQ-167
ssot_status: published
sot: Develop@a8a1edd713d6db6db61d42ed4eacf6a9e8737d07
<<<
RELATIONS:
- TYPE: Parent
  VALUE: USR-VAL-041

[REQUIREMENT]
UID: REQ-VAL-168
STATUS: Active
TITLE: REQ-VAL-168: MainLayout wraps game pages; LeftNavBar modules come from game manifests (Auctio
STATEMENT: >>>
MainLayout wraps game pages; LeftNavBar modules come from game manifests (Auction + Raid for RO; Hall for AG).
<<<
COMMENT: >>>
domain: Frontend shell/UX
priority: must
type: system
constraints: Live Develop behavior only; Do not import Firebase Requirements.md wording
acceptance_criteria: MainLayout wraps game pages; LeftNavBar modules come from game manifests (Auction + Raid for RO; Hall for AG).
source_draft: D-REQ-168
ssot_status: published
sot: Develop@a8a1edd713d6db6db61d42ed4eacf6a9e8737d07
<<<
RELATIONS:
- TYPE: Parent
  VALUE: USR-VAL-041

[REQUIREMENT]
UID: REQ-VAL-169
STATUS: Active
TITLE: REQ-VAL-169: Help Guide modal loads auction/raid embed URLs from settings/help; mobile opens 
STATEMENT: >>>
Help Guide modal loads auction/raid embed URLs from settings/help; mobile opens external tab.
<<<
COMMENT: >>>
domain: Frontend shell/UX
priority: must
type: system
constraints: Live Develop behavior only; Do not import Firebase Requirements.md wording
acceptance_criteria: Help Guide modal loads auction/raid embed URLs from settings/help; mobile opens external tab.
source_draft: D-REQ-169
ssot_status: published
sot: Develop@a8a1edd713d6db6db61d42ed4eacf6a9e8737d07
<<<
RELATIONS:
- TYPE: Parent
  VALUE: USR-VAL-041

[REQUIREMENT]
UID: REQ-VAL-170
STATUS: Active
TITLE: REQ-VAL-170: Workspace Settings page at `/workspace`; Choose Game at `/workspace/games`; Bill
STATEMENT: >>>
Workspace Settings page at `/workspace`; Choose Game at `/workspace/games`; Billing at `/workspace/billing`; RO setup at `/games/ragnarok-origin/setup`.
<<<
COMMENT: >>>
domain: Frontend shell/UX
priority: must
type: system
constraints: Live Develop behavior only; Do not import Firebase Requirements.md wording
acceptance_criteria: Workspace Settings page at `/workspace`; Choose Game at `/workspace/games`; Billing at `/workspace/billing`; RO setup at `/games/ragnarok-origin/setup`.
source_draft: D-REQ-170
ssot_status: published
sot: Develop@a8a1edd713d6db6db61d42ed4eacf6a9e8737d07
<<<
RELATIONS:
- TYPE: Parent
  VALUE: USR-VAL-041

[REQUIREMENT]
UID: REQ-VAL-171
STATUS: Active
TITLE: REQ-VAL-171: apiFetch on 402 redirects browser to `/workspace/billing`.
STATEMENT: >>>
apiFetch on 402 redirects browser to `/workspace/billing`.
<<<
COMMENT: >>>
domain: Frontend shell/UX
priority: must
type: system
constraints: Live Develop behavior only; Do not import Firebase Requirements.md wording
acceptance_criteria: apiFetch on 402 redirects browser to `/workspace/billing`.
source_draft: D-REQ-171
ssot_status: published
sot: Develop@a8a1edd713d6db6db61d42ed4eacf6a9e8737d07
<<<
RELATIONS:
- TYPE: Parent
  VALUE: USR-VAL-042

[REQUIREMENT]
UID: REQ-VAL-172
STATUS: Active
TITLE: REQ-VAL-172: Officer Role Picker / Discord Sign-In button / Valhalla brand lockup components 
STATEMENT: >>>
Officer Role Picker / Discord Sign-In button / Valhalla brand lockup components support onboard and landing flows.
<<<
COMMENT: >>>
domain: Frontend shell/UX
priority: must
type: system
constraints: Live Develop behavior only; Do not import Firebase Requirements.md wording
acceptance_criteria: Officer Role Picker / Discord Sign-In button / Valhalla brand lockup components support onboard and landing flows.
source_draft: D-REQ-172
ssot_status: published
sot: Develop@a8a1edd713d6db6db61d42ed4eacf6a9e8737d07
<<<
RELATIONS:
- TYPE: Parent
  VALUE: USR-VAL-042

[[/SECTION]]

[[SECTION]]
TITLE: Mimic Book (REQ-ROO-202 .. REQ-ROO-204)

[REQUIREMENT]
UID: REQ-ROO-202
STATUS: Active
TITLE: REQ-ROO-202: Live Claim shows names for everyone holding a slot
STATEMENT: >>>
Live Claim shows names for everyone holding a slot
<<<
COMMENT: >>>
domain: Mimic Book
priority: unspecified
type: software
constraints: (none)
acceptance_criteria: Opening the Mimic Book while a session is active shows each slot holder's roster display name, including members not otherwise loaded on the page. | Members with no roster name are not added. | The names are sent with the session but are not saved into the stored session. | On the 24h fresh reset the names list is empty.
source_draft: f38e137/mints-ROO.json
ssot_status: published
sot: xWhiteSpace/ROOGuildApp@f38e1378c7cca457fbf8de8e8355d59994f77fc8
<<<
RELATIONS:
- TYPE: Parent
  VALUE: USR-ROO-022

[REQUIREMENT]
UID: REQ-ROO-203
STATUS: Active
TITLE: REQ-ROO-203: Committing replaces an ID-only winner name with the roster name
STATEMENT: >>>
Committing replaces an ID-only winner name with the roster name
<<<
COMMENT: >>>
domain: Mimic Book
priority: unspecified
type: software
constraints: (none)
acceptance_criteria: If a winner's name arrives as only digits (a Discord ID), loot history, awards and forced adds record the roster display name. | Any other given name is kept as given. | With no name and no roster name, the record says Unknown Member.
source_draft: f38e137/mints-ROO.json
ssot_status: published
sot: xWhiteSpace/ROOGuildApp@f38e1378c7cca457fbf8de8e8355d59994f77fc8
<<<
RELATIONS:
- TYPE: Parent
  VALUE: USR-ROO-022

[REQUIREMENT]
UID: REQ-ROO-204
STATUS: Active
TITLE: REQ-ROO-204: A Discord claim updates the member's roster name
STATEMENT: >>>
A Discord claim updates the member's roster name
<<<
COMMENT: >>>
domain: Mimic Book
priority: unspecified
type: software
constraints: (none)
acceptance_criteria: After a member claims a slot from Discord and passes the collision check, their roster display name becomes the name used for the claim.
source_draft: f38e137/mints-ROO.json
ssot_status: published
sot: xWhiteSpace/ROOGuildApp@f38e1378c7cca457fbf8de8e8355d59994f77fc8
<<<
RELATIONS:
- TYPE: Parent
  VALUE: USR-ROO-022

[[/SECTION]]

[[SECTION]]
TITLE: Data isolation (REQ-VAL-205 .. REQ-VAL-210)

[REQUIREMENT]
UID: REQ-VAL-205
STATUS: Active
TITLE: REQ-VAL-205: Each game's records are stored and read only as that game, and no-game code is r
STATEMENT: >>>
Each game's records are stored and read only as that game, and no-game code is refused
<<<
COMMENT: >>>
domain: Data isolation
priority: unspecified
type: software
constraints: (none)
acceptance_criteria: Roster, auction requests, awards, loot history, commitments, schedule instances, special events and documents saved from Origin cannot be read or changed from Ragnarok 3, and those saved from Ragnarok 3 cannot be read or changed from Origin, in the same workspace. | Records saved before this change count as Origin; Adventurer Guild documents count as Adventurer Guild. | A request, Discord card press or background job that reads or writes game data with no game set is refused with a 'select a game' error and reads or writes nothing; it never falls back to Origin.
source_draft: f38e137/mints-ROO.json
ssot_status: published
sot: xWhiteSpace/ROOGuildApp@f38e1378c7cca457fbf8de8e8355d59994f77fc8
<<<
RELATIONS:
- TYPE: Parent
  VALUE: USR-VAL-044

[REQUIREMENT]
UID: REQ-VAL-206
STATUS: Active
TITLE: REQ-VAL-206: Same Discord member can be on each game's roster, changed independently both way
STATEMENT: >>>
Same Discord member can be on each game's roster, changed independently both ways
<<<
COMMENT: >>>
domain: Data isolation
priority: unspecified
type: software
constraints: (none)
acceptance_criteria: One Discord member can have one roster entry per game in the same workspace. | Changing that member's Origin roster entry leaves their Ragnarok 3 entry unchanged. | Changing that member's Ragnarok 3 roster entry leaves their Origin entry unchanged.
source_draft: f38e137/mints-ROO.json
ssot_status: published
sot: xWhiteSpace/ROOGuildApp@f38e1378c7cca457fbf8de8e8355d59994f77fc8
<<<
RELATIONS:
- TYPE: Parent
  VALUE: USR-VAL-044

[REQUIREMENT]
UID: REQ-VAL-207
STATUS: Active
TITLE: REQ-VAL-207: Game settings saved apart from shared workspace settings
STATEMENT: >>>
Game settings saved apart from shared workspace settings
<<<
COMMENT: >>>
domain: Data isolation
priority: unspecified
type: software
constraints: Shared keys: guild name, timezone, admin roles, logo.
acceptance_criteria: Saving one game's settings does not change another game's settings or the shared workspace keys (except Origin, which still saves the shared keys). | Reading a game's settings gives defaults, then that game's defaults, then shared workspace values, then the game's own values, later ones winning. | After a game's settings are saved, the next read for that game returns the new values and other games' reads are unaffected.
source_draft: f38e137/mints-ROO.json
ssot_status: published
sot: xWhiteSpace/ROOGuildApp@f38e1378c7cca457fbf8de8e8355d59994f77fc8
<<<
RELATIONS:
- TYPE: Parent
  VALUE: USR-VAL-044

[REQUIREMENT]
UID: REQ-VAL-208
STATUS: Active
TITLE: REQ-VAL-208: Existing Origin settings carry over on upgrade
STATEMENT: >>>
Existing Origin settings carry over on upgrade
<<<
COMMENT: >>>
domain: Data isolation
priority: unspecified
type: software
constraints: (none)
acceptance_criteria: On upgrade, Origin settings in the workspace record are copied to Origin's game settings only when Origin's game settings are empty, then the workspace record keeps only the four shared keys. | Leftover Origin keys found later are copied on read.
source_draft: f38e137/mints-ROO.json
ssot_status: published
sot: xWhiteSpace/ROOGuildApp@f38e1378c7cca457fbf8de8e8355d59994f77fc8
<<<
RELATIONS:
- TYPE: Parent
  VALUE: USR-VAL-044

[REQUIREMENT]
UID: REQ-VAL-209
STATUS: Active
TITLE: REQ-VAL-209: Login adds a roster entry only when Origin is enabled
STATEMENT: >>>
Login adds a roster entry only when Origin is enabled
<<<
COMMENT: >>>
domain: Data isolation
priority: unspecified
type: software
constraints: (none)
acceptance_criteria: Signing in to a workspace without Origin enabled creates or updates no roster entry. | With Origin enabled, sign-in updates the Origin roster entry.
source_draft: f38e137/mints-ROO.json
ssot_status: published
sot: xWhiteSpace/ROOGuildApp@f38e1378c7cca457fbf8de8e8355d59994f77fc8
<<<
RELATIONS:
- TYPE: Parent
  VALUE: USR-VAL-044

[REQUIREMENT]
UID: REQ-VAL-210
STATUS: Active
TITLE: REQ-VAL-210: Origin automation runs only for workspaces with Origin enabled
STATEMENT: >>>
Origin automation runs only for workspaces with Origin enabled
<<<
COMMENT: >>>
domain: Data isolation
priority: unspecified
type: system
constraints: (none)
acceptance_criteria: The schedule tick, leave-credit seeding and live-raid resume at startup run only for workspaces with Origin enabled, and only on Origin data.
source_draft: f38e137/mints-ROO.json
ssot_status: published
sot: xWhiteSpace/ROOGuildApp@f38e1378c7cca457fbf8de8e8355d59994f77fc8
<<<
RELATIONS:
- TYPE: Parent
  VALUE: USR-VAL-044

[[/SECTION]]

[[SECTION]]
TITLE: Discord (REQ-VAL-211)

[REQUIREMENT]
UID: REQ-VAL-211
STATUS: Active
TITLE: REQ-VAL-211: Origin card deploys are gated to Origin
STATEMENT: >>>
Origin card deploys are gated to Origin
<<<
COMMENT: >>>
domain: Discord
priority: unspecified
type: software
constraints: (none)
acceptance_criteria: Every Origin card deploy (request, GvG readiness/attendance, party, party-screenshot and onboarding cards, at the root and the attendance-alias addresses) is accepted only when Origin is enabled for the workspace; otherwise it is refused and nothing is posted. | An Origin card deploy reads and writes only Origin data, and posts, edits or removes no Ragnarok 3 card. | A Ragnarok 3 card deploy posts, edits or removes no Origin card and writes no Origin record.
source_draft: f38e137/answers-2026-10-08/mints.json
ssot_status: published
sot: xWhiteSpace/ROOGuildApp@f38e1378c7cca457fbf8de8e8355d59994f77fc8
<<<
RELATIONS:
- TYPE: Parent
  VALUE: USR-VAL-019

[[/SECTION]]

[[SECTION]]
TITLE: Ragnarok 3 (REQ-R3-001 .. REQ-R3-008)

[REQUIREMENT]
UID: REQ-R3-001
STATUS: Active
TITLE: REQ-R3-001: `ragnarok-3` is a known Game Stack pack enabled independently on the same Discord tenant.
STATEMENT: >>>
`ragnarok-3` is a known Game Stack pack. Officers enable it on the same Discord tenant as Origin or Adventurer Guild. Enable/disable hides access and keeps stored R3 rows.
<<<
COMMENT: >>>
domain: Ragnarok 3
priority: must
type: system
acceptance_criteria: `ragnarok-3` is a known Game Stack pack. Officers enable it on the same Discord tenant as Origin or Adventurer Guild. Enable/disable hides access and keeps stored R3 rows.
ssot_status: published
<<<
RELATIONS:
- TYPE: Parent
  VALUE: USR-VAL-011

[REQUIREMENT]
UID: REQ-R3-002
STATUS: Active
TITLE: REQ-R3-002: Game-scoped operational rows are `(tenant_id, game_id, …)`; R3 writes `game_id=ragnarok-3`.
STATEMENT: >>>
Members, auction tables, commitments, schedule rows, json_docs, and `game_settings` are keyed by `(tenant_id, game_id, …)`. Ragnarok 3 reads and writes only `game_id=ragnarok-3`. Workspace keys stay on `tenant_settings`.
<<<
COMMENT: >>>
domain: Ragnarok 3
priority: must
type: system
acceptance_criteria: Members, auction tables, commitments, schedule rows, json_docs, and `game_settings` are keyed by `(tenant_id, game_id, …)`. Ragnarok 3 reads and writes only `game_id=ragnarok-3`. Workspace keys stay on `tenant_settings`.
ssot_status: published
<<<
RELATIONS:
- TYPE: Parent
  VALUE: USR-VAL-039

[REQUIREMENT]
UID: REQ-R3-003
STATUS: Active
TITLE: REQ-R3-003: The same `discord_id` may have Origin and R3 `members` rows.
STATEMENT: >>>
A Discord user can have two `members` rows on one tenant: one with `game_id=ragnarok-origin` and one with `game_id=ragnarok-3`.
<<<
COMMENT: >>>
domain: Ragnarok 3
priority: must
type: system
acceptance_criteria: A Discord user can have two `members` rows on one tenant: one with `game_id=ragnarok-origin` and one with `game_id=ragnarok-3`.
ssot_status: published
<<<
RELATIONS:
- TYPE: Parent
  VALUE: USR-VAL-011

[REQUIREMENT]
UID: REQ-R3-004
STATUS: Active
TITLE: REQ-R3-004: R3 Game Settings live in `game_settings` for `ragnarok-3` and must not mutate Origin.
STATEMENT: >>>
R3 settings save writes `game_settings(tenant_id, ragnarok-3)` only. It must not mutate Origin `game_settings` or workspace-only keys on `tenant_settings`.
<<<
COMMENT: >>>
domain: Ragnarok 3
priority: must
type: system
acceptance_criteria: R3 settings save writes `game_settings(tenant_id, ragnarok-3)` only. It must not mutate Origin `game_settings` or workspace-only keys on `tenant_settings`.
ssot_status: published
<<<
RELATIONS:
- TYPE: Parent
  VALUE: USR-VAL-011

[REQUIREMENT]
UID: REQ-R3-005
STATUS: Active
TITLE: REQ-R3-005: `/api/ragnarok-3` requires `requireGame(ragnarok-3)`; Origin APIs cannot read R3 json_docs.
STATEMENT: >>>
Mounted `/api/ragnarok-3` requires `requireGame('ragnarok-3')` else 403 `game_required`. Origin mounts set `gameId=ragnarok-origin` and cannot see R3-stamped json_docs or members.
<<<
COMMENT: >>>
domain: Ragnarok 3
priority: must
type: system
acceptance_criteria: Mounted `/api/ragnarok-3` requires `requireGame('ragnarok-3')` else 403 `game_required`. Origin mounts set `gameId=ragnarok-origin` and cannot see R3-stamped json_docs or members.
ssot_status: published
<<<
RELATIONS:
- TYPE: Parent
  VALUE: USR-VAL-012

[REQUIREMENT]
UID: REQ-R3-006
STATUS: Active
TITLE: REQ-R3-006: R3 SPA lives under `/games/ragnarok-3` with no setupPath; `gameIdForPath` matches R3 first.
STATEMENT: >>>
R3 has `pathPrefix` `/games/ragnarok-3`, `settingsPath` `/games/ragnarok-3/settings`, and no `setupPath`. `gameIdForPath` returns `ragnarok-3` for those routes and must not fall through to Origin.
<<<
COMMENT: >>>
domain: Ragnarok 3
priority: must
type: system
acceptance_criteria: R3 has `pathPrefix` `/games/ragnarok-3`, `settingsPath` `/games/ragnarok-3/settings`, and no `setupPath`. `gameIdForPath` returns `ragnarok-3` for those routes and must not fall through to Origin.
ssot_status: published
<<<
RELATIONS:
- TYPE: Parent
  VALUE: USR-VAL-011

[REQUIREMENT]
UID: REQ-R3-007
STATUS: Active
TITLE: REQ-R3-007: R3 calendar is R3-only and is not registered in scheduleContributors.
STATEMENT: >>>
R3 week instances, special events, and commitments use game-stamped schedule tables. R3 must not register a schedule contributor that would leak into Adventurer Guild events.
<<<
COMMENT: >>>
domain: Ragnarok 3
priority: must
type: system
acceptance_criteria: R3 week instances, special events, and commitments use game-stamped schedule tables. R3 must not register a schedule contributor that would leak into Adventurer Guild events.
ssot_status: published
<<<
RELATIONS:
- TYPE: Parent
  VALUE: USR-VAL-011

[REQUIREMENT]
UID: REQ-R3-008
STATUS: Active
TITLE: REQ-R3-008: R3 v1 is web-only: no Discord channel map, voice presence, or Origin war automation.
STATEMENT: >>>
Ragnarok 3 v1 does not write `discord_channels` auction/war maps, does not poll Discord voice, and does not run Origin war-room automation or Discord deploy cards.
<<<
COMMENT: >>>
domain: Ragnarok 3
priority: must
type: system
acceptance_criteria: Ragnarok 3 v1 does not write `discord_channels` auction/war maps, does not poll Discord voice, and does not run Origin war-room automation or Discord deploy cards.
ssot_status: published
<<<
RELATIONS:
- TYPE: Parent
  VALUE: USR-VAL-011

[[/SECTION]]
