[DOCUMENT]
TITLE: ROO Design Summary (left-side tips)
UID: DOC-ROO-DESIGN
VERSION: 0.1
OPTIONS:
  MARKUP: Text

[[SECTION]]
TITLE: Left-side status

[TEXT]
STATEMENT: >>>
Published counts and next free ids (from SSOT):
- FNC published=212; tip=FNC-ROO-213
- API published=118; tip=API-ROO-119
- CMP published=29; tip=CMP-ROO-030
- INT published=121; tip=INT-ROO-122
- UNT published=223; tip=UNT-ROO-224

This document summarizes by domain with ID ranges only (not every design node).
Full node JSON remains in SSOT registries under interfaces/, structure/, units/.
SSOT sync 2026-10-10 (JST): graph 91; source xWhiteSpace/ROOGuildApp@f38e1378c7cca457fbf8de8e8355d59994f77fc8. Published in SSOT ≠ proven; no EVD; every TST is execution_status blocked_on_tooling, evidence_status none.
<<<

[[/SECTION]]

[[SECTION]]
TITLE: FNC — Functional specs

[TEXT]
STATEMENT: >>>
Published count: 212
ID span: FNC-VAL-001 .. FNC-ROO-212
Next tip: FNC-ROO-213

Domain map:
- Platform/Auth: count=6; range=FNC-VAL-001 .. FNC-VAL-006
- Tenant/Workspace: count=9; range=FNC-VAL-007 .. FNC-VAL-015
- Games catalog: count=8; range=FNC-VAL-016 .. FNC-VAL-023
- Billing/Capacity: count=13; range=FNC-VAL-024 .. FNC-VAL-036
- Discord bot/Channels: count=23; range=FNC-VAL-037 .. FNC-VAL-052, FNC-VAL-191, FNC-VAL-195, FNC-VAL-198 .. FNC-VAL-202
- Auction/Requests: count=28; range=FNC-ROO-053 .. FNC-ROO-075, FNC-ROO-175, FNC-ROO-180 .. FNC-ROO-182, FNC-ROO-186
- Attendance/Roster: count=16; range=FNC-ROO-076 .. FNC-ROO-089, FNC-ROO-174, FNC-ROO-188
- Scheduler/RSVP: count=17; range=FNC-ROO-090 .. FNC-ROO-101, FNC-ROO-177 .. FNC-ROO-179, FNC-ROO-184, FNC-ROO-190
- Raid compose/Party: count=29; range=FNC-ROO-102 .. FNC-ROO-125, FNC-ROO-176, FNC-ROO-183, FNC-ROO-187, FNC-ROO-192 .. FNC-ROO-193
- Live Raid/Voice: count=20; range=FNC-ROO-126 .. FNC-ROO-141, FNC-ROO-185, FNC-ROO-189, FNC-ROO-194, FNC-ROO-196
- OCR/GVG Attendance: count=9; range=FNC-ROO-142 .. FNC-ROO-150
- Adventurer Guild: count=9; range=FNC-ROO-151 .. FNC-ROO-158, FNC-ROO-197
- Data isolation/Storage: count=9; range=FNC-VAL-159 .. FNC-VAL-167
- Frontend shell/UX: count=6; range=FNC-VAL-168 .. FNC-VAL-173
- (none): count=10; range=FNC-ROO-203 .. FNC-ROO-212
<<<

[[/SECTION]]

[[SECTION]]
TITLE: API — Interfaces

[TEXT]
STATEMENT: >>>
Published count: 118
ID span: API-VAL-001 .. API-VAL-118 (VAL platform and ROO Origin)
Next tip: API-ROO-119

Domain map:
- Platform/Auth: count=5; range=API-VAL-001 .. API-VAL-005
- Tenant/Workspace: count=9; range=API-VAL-006 .. API-VAL-014
- Games catalog: count=3; range=API-VAL-015 .. API-VAL-017
- Billing/Capacity: count=6; range=API-VAL-018 .. API-VAL-023
- Discord bot/Channels: count=8; range=API-VAL-024 .. API-VAL-030, API-VAL-118
- Auction/Requests: count=18; range=API-ROO-031 .. API-ROO-047, API-ROO-115
- Attendance/Roster: count=13; range=API-ROO-048 .. API-ROO-059, API-ROO-116
- Scheduler/RSVP: count=9; range=API-ROO-060 .. API-ROO-068
- Raid compose/Party: count=20; range=API-ROO-069 .. API-ROO-088
- Live Raid/Voice: count=12; range=API-ROO-089 .. API-ROO-099, API-ROO-117
- OCR/GVG Attendance: count=8; range=API-ROO-100 .. API-ROO-107
- Adventurer Guild: count=7; range=API-ROO-108 .. API-ROO-114
<<<

[[/SECTION]]

[[SECTION]]
TITLE: CMP — Components

[TEXT]
STATEMENT: >>>
Published count: 29
ID span: CMP-VAL-001 .. CMP-ROO-029
Next tip: CMP-ROO-030

Domain map:
- Platform/Auth: count=4; range=CMP-VAL-001 .. CMP-VAL-004
- Tenant/Workspace: count=2; range=CMP-VAL-005 .. CMP-VAL-006
- Games catalog: count=2; range=CMP-VAL-007 .. CMP-VAL-008
- Billing/Capacity: count=1; range=CMP-VAL-009
- Discord bot/Channels: count=2; range=CMP-VAL-010 .. CMP-VAL-011
- Auction/Requests: count=2; range=CMP-ROO-012 .. CMP-ROO-013
- Attendance/Roster: count=3; range=CMP-ROO-014 .. CMP-ROO-016
- Scheduler/RSVP: count=2; range=CMP-ROO-017 .. CMP-ROO-018
- Raid compose/Party: count=3; range=CMP-ROO-019 .. CMP-ROO-021
- Live Raid/Voice: count=3; range=CMP-ROO-022 .. CMP-ROO-023, CMP-ROO-029
- OCR/GVG Attendance: count=1; range=CMP-ROO-024
- Adventurer Guild: count=2; range=CMP-ROO-025 .. CMP-ROO-026
- Data isolation/Storage: count=2; range=CMP-VAL-027 .. CMP-VAL-028
<<<

[[/SECTION]]

[[SECTION]]
TITLE: INT — Integration seams

[TEXT]
STATEMENT: >>>
Published count: 121
ID span: INT-VAL-001 .. INT-ROO-121
Next tip: INT-ROO-122

Domain map:
- Platform/Auth: count=5; range=INT-VAL-001 .. INT-VAL-005
- Tenant/Workspace: count=9; range=INT-VAL-006 .. INT-VAL-014
- Games catalog: count=3; range=INT-VAL-015 .. INT-VAL-017
- Billing/Capacity: count=6; range=INT-VAL-018 .. INT-VAL-023
- Discord bot/Channels: count=8; range=INT-VAL-024 .. INT-VAL-030, INT-VAL-118
- Auction/Requests: count=18; range=INT-ROO-031 .. INT-ROO-047, INT-ROO-115
- Attendance/Roster: count=13; range=INT-ROO-048 .. INT-ROO-059, INT-ROO-116
- Scheduler/RSVP: count=9; range=INT-ROO-060 .. INT-ROO-068
- Raid compose/Party: count=20; range=INT-ROO-069 .. INT-ROO-088
- Live Raid/Voice: count=14; range=INT-ROO-089 .. INT-ROO-099, INT-ROO-117, INT-ROO-120 .. INT-ROO-121
- OCR/GVG Attendance: count=8; range=INT-ROO-100 .. INT-ROO-107
- Adventurer Guild: count=7; range=INT-ROO-108 .. INT-ROO-114
- (none): count=1; range=INT-ROO-119
<<<

[[/SECTION]]

[[SECTION]]
TITLE: UNT — Units

[TEXT]
STATEMENT: >>>
Published count: 223
ID span: UNT-VAL-001 .. UNT-ROO-223
Next tip: UNT-ROO-224

Domain map:
- Platform/Auth: count=17; range=UNT-VAL-001 .. UNT-VAL-017
- Tenant/Workspace: count=9; range=UNT-VAL-018 .. UNT-VAL-026
- Games catalog: count=10; range=UNT-VAL-027 .. UNT-VAL-035, UNT-VAL-213
- Billing/Capacity: count=12; range=UNT-VAL-036 .. UNT-VAL-047
- Discord bot/Channels: count=16; range=UNT-VAL-048 .. UNT-VAL-063
- Auction/Requests: count=22; range=UNT-ROO-064 .. UNT-ROO-085
- Attendance/Roster: count=14; range=UNT-ROO-086 .. UNT-ROO-099
- Scheduler/RSVP: count=12; range=UNT-ROO-100 .. UNT-ROO-111
- Raid compose/Party: count=24; range=UNT-ROO-112 .. UNT-ROO-135
- Live Raid/Voice: count=16; range=UNT-ROO-136 .. UNT-ROO-151
- OCR/GVG Attendance: count=9; range=UNT-ROO-152 .. UNT-ROO-160
- Adventurer Guild: count=8; range=UNT-ROO-161 .. UNT-ROO-168
- Data isolation/Storage: count=11; range=UNT-VAL-169 .. UNT-VAL-177, UNT-VAL-218 .. UNT-VAL-219
- Frontend shell/UX: count=6; range=UNT-VAL-178 .. UNT-VAL-183
- ROO delta 2026-10-03: count=24; range=UNT-ROO-184 .. UNT-ROO-207
- Discord onboarding: count=5; range=UNT-ROO-208 .. UNT-ROO-212
- Auction/Mimic Book: count=2; range=UNT-ROO-214, UNT-ROO-216
- SPA/Mimic Book: count=1; range=UNT-ROO-215
- Discord/Auction: count=1; range=UNT-ROO-217
- Settings/Storage: count=2; range=UNT-ROO-220 .. UNT-ROO-221
- Auth/Roster: count=1; range=UNT-ROO-222
- Discord/Automation: count=1; range=UNT-ROO-223
<<<

[[/SECTION]]

[[SECTION]]
TITLE: Cross-kind tip snapshot

[TEXT]
STATEMENT: >>>
Tips (next free): FNC=FNC-ROO-213, API=API-ROO-119, CMP=CMP-ROO-030, INT=INT-ROO-122, UNT=UNT-ROO-224
Earlier Staging note (kept): GVG readiness rematerialize published FNC-191 / FNC-201 / INT-117 / UNT-201 / UNT-213. Discord onboarding hub published FNC-198..200 / API-118..119 / INT-115..116 / UNT-208..212. Catch-up TST verifies already used FNC-174..197.
Ragnarok 3 design summary: design/ro3_summary.sdoc.
<<<

[[/SECTION]]
